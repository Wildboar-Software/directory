EnrollmentMessageSyntax-2009
{iso(1) identified-organization(3) dod(6) internet(1)
security(5) mechanisms(5) pkix(7) id-mod(0) id-mod-cmc2002-02(53)}
DEFINITIONS IMPLICIT TAGS ::= BEGIN
EXPORTS ALL;
IMPORTS

    ATTRIBUTE
        FROM InformationFramework
        {joint-iso-itu-t ds(5) module(1) informationFramework(1) 9}
        WITH SUCCESSORS

    Extension
        FROM AuthenticationFramework
        {joint-iso-itu-t ds(5) module(1) authenticationFramework(7) 9}
        WITH SUCCESSORS

    ;

-- Attributes

id-ExtensionReq OBJECT IDENTIFIER ::= {iso(1) member-body(2) us(840)
    rsadsi(113549) pkcs(1) pkcs-9(9) 14}

ExtensionReq ::= SEQUENCE SIZE (1..MAX) OF Extension

at-extension-req ATTRIBUTE ::= {
    WITH SYNTAX     ExtensionReq
    ID              id-ExtensionReq
}

id-aa OBJECT IDENTIFIER ::= { iso(1) member-body(2) us(840)
    rsadsi(113549) pkcs(1) pkcs-9(9) smime(16) id-aa(2)}

id-aa-cmc-unsignedData OBJECT IDENTIFIER ::= {id-aa 34}

BodyPartID ::= INTEGER(0..4294967295)

BodyPartPath ::= SEQUENCE SIZE (1..MAX) OF BodyPartID

CMCUnsignedData ::= SEQUENCE {
    bodyPartPath        BodyPartPath,
    identifier          TYPE-IDENTIFIER.&id,
    content             TYPE-IDENTIFIER.&Type
}

aa-cmc-unsignedData ATTRIBUTE ::= {
    WITH SYNTAX	    CMCUnsignedData
    ID			    id-at-aa-cmc-unsignedData
}

END
