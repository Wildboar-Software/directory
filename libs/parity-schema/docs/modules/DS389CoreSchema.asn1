DS389CoreSchema {
    iso(1) identified-organization(3) dod(6) internet(1) private(4)
    enterprise(1) wildboar(56490) module(1) ds389-core-schema(47)
}
DEFINITIONS
EXPLICIT TAGS
EXTENSIBILITY IMPLIED
::=
BEGIN

EXPORTS ALL;

IMPORTS

    ATTRIBUTE
        FROM InformationFramework
        {joint-iso-itu-t ds(5) module(1) informationFramework(1) 9}
        WITH SUCCESSORS

    integer, integerMatch, integerOrderingMatch
		FROM SelectedAttributeTypes
		{joint-iso-itu-t ds(5) module(1) selectedAttributeTypes(5) 9}
		WITH SUCCESSORS

    ;

id-at-numSubordinates OBJECT IDENTIFIER ::= { 1 3 1 1 4 1 453 16 2 103 }

numSubordinates ATTRIBUTE ::= {
    WITH SYNTAX 				INTEGER (0..MAX)
    EQUALITY MATCHING RULE 		integerMatch
    ORDERING MATCHING RULE      integerOrderingMatch
    SINGLE VALUE                TRUE
    NO USER MODIFICATION        TRUE
    USAGE                       directoryOperation
	LDAP-SYNTAX 				integer.&id
	LDAP-NAME 					{"numSubordinates"}
	LDAP-DESC					"count of immediate subordinates"
    ID                          id-at-numSubordinates
}

-- Core389.ldif was skipped.

END
