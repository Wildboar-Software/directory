UUID {
    iso(1) identified-organization(3) dod(6) internet(1) private(4)
    enterprise(1) wildboar(56490) module(1) uuid(29)
}
DEFINITIONS
EXPLICIT TAGS
EXTENSIBILITY IMPLIED
::=
BEGIN

EXPORTS ALL;

IMPORTS

    ATTRIBUTE, MATCHING-RULE, SYNTAX-NAME, top
        FROM InformationFramework
        {joint-iso-itu-t ds(5) module(1) informationFramework(1) 9}
        WITH SUCCESSORS

    UUID
		FROM SelectedAttributeTypes
		{joint-iso-itu-t ds(5) module(1) selectedAttributeTypes(5) 9}
		WITH SUCCESSORS

    ;

id-lsx-uuid                 OBJECT IDENTIFIER ::= { 1 3 6 1 1 16 1 }
id-uuidMatch                OBJECT IDENTIFIER ::= { 1 3 6 1 1 16 2 }
id-uuidOrderingMatch        OBJECT IDENTIFIER ::= { 1 3 6 1 1 16 3 }
id-at-entryUUID             OBJECT IDENTIFIER ::= { 1 3 6 1 1 16 4 }

uuid SYNTAX-NAME ::= {
    LDAP-DESC               "UUID"
    DIRECTORY SYNTAX        UUID
    ID                      id-lsx-uuid
}

uuidMatch MATCHING-RULE ::= {
    SYNTAX                  UUID
    LDAP-SYNTAX             uuid.&id
    LDAP-NAME               {"uuidMatch"}
    ID                      id-uuidMatch
}

uuidOrderingMatch MATCHING-RULE ::= {
    SYNTAX                  UUID
    LDAP-SYNTAX             uuid.&id
    LDAP-NAME               {"uuidOrderingMatch"}
    ID                      id-uuidOrderingMatch
}

entryUUID ATTRIBUTE ::= {
    WITH SYNTAX             UUID
    EQUALITY MATCHING RULE  uuidMatch
    ORDERING MATCHING RULE  uuidOrderingMatch
    SINGLE VALUE            TRUE
    NO USER MODIFICATION    TRUE
    USAGE                   directoryOperation
    LDAP-SYNTAX             uuid.&id
    LDAP-NAME               {"entryUUID"}
    ID                      id-at-entryUUID
}

END
