Misc {
    iso(1) identified-organization(3) dod(6) internet(1) private(4)
    enterprise(1) wildboar(56490) module(1) misc-schema(25)
}
DEFINITIONS
EXPLICIT TAGS
EXTENSIBILITY IMPLIED
::=
BEGIN

EXPORTS ALL;

IMPORTS

    ATTRIBUTE, OBJECT-CLASS, top, SYNTAX-NAME
        FROM InformationFramework
        {joint-iso-itu-t ds(5) module(1) informationFramework(1) 9}
        WITH SUCCESSORS

    caseIgnoreIA5Match, caseIgnoreIA5SubstringsMatch, ia5String
		FROM SelectedAttributeTypes
		{joint-iso-itu-t ds(5) module(1) selectedAttributeTypes(5) 9}
		WITH SUCCESSORS

    ;

mailLocalAddress ATTRIBUTE ::= {
    WITH SYNTAX                 IA5String
    EQUALITY MATCHING RULE 		caseIgnoreIA5Match
	SUBSTRINGS MATCHING RULE 	caseIgnoreIA5SubstringsMatch
	LDAP-SYNTAX 				ia5String.&id
    LDAP-NAME                   {"mailLocalAddress"}
    LDAP-DESC "RFC822 email address of this recipient"
    ID                          { 2 16 840 1 113730 3 1 13 }
}

mailHost ATTRIBUTE ::= {
    WITH SYNTAX                 IA5String
    EQUALITY MATCHING RULE 		caseIgnoreIA5Match
	SUBSTRINGS MATCHING RULE 	caseIgnoreIA5SubstringsMatch
    SINGLE VALUE                TRUE
	LDAP-SYNTAX 				ia5String.&id
    LDAP-NAME                   {"mailHost"}
    LDAP-DESC "FQDN of the SMTP/MTA of this recipient"
    ID                          { 2 16 840 1 113730 3 1 18 }
}

mailRoutingAddress ATTRIBUTE ::= {
    WITH SYNTAX                 IA5String
    EQUALITY MATCHING RULE 		caseIgnoreIA5Match
	SUBSTRINGS MATCHING RULE 	caseIgnoreIA5SubstringsMatch
    SINGLE VALUE                TRUE
	LDAP-SYNTAX 				ia5String.&id
    LDAP-NAME                   {"mailRoutingAddress"}
    LDAP-DESC "RFC822 routing address of this recipient"
    ID                          { 2 16 840 1 113730 3 1 47 }
}

-- # I-D leaves this OID TBD.
-- # iPlanet uses 2.16.840.1.113.730.3.2.147 but that is an
-- # improperly delegated OID.  A typo is likely.
-- objectclass ( 2.16.840.1.113730.3.2.147
-- 	NAME 'inetLocalMailRecipient'
-- 	DESC 'Internet local mail recipient'
-- 	SUP top AUXILIARY
-- 	MAY	( mailLocalAddress $ mailHost $ mailRoutingAddress ) )

-- #-----------------------------------------------------------
-- # draft-srivastava-ldap-mail-00.txt !!!EXPIRED!!!
-- #	(a work in progress)
-- #
-- attributetype ( 1.3.6.1.4.1.42.2.27.2.1.15
-- 	NAME 'rfc822MailMember'
-- 	DESC 'rfc822 mail address of group member(s)'
-- 	EQUALITY caseIgnoreIA5Match
-- 	SYNTAX 1.3.6.1.4.1.1466.115.121.1.26 )

-- #-----------------------------------------------------------
-- # !!!no I-D!!!
-- #	(a work in progress)
-- #
-- objectclass ( 1.3.6.1.4.1.42.2.27.1.2.5
-- 	NAME 'nisMailAlias'
-- 	DESC 'NIS mail alias'
-- 	SUP top STRUCTURAL
-- 	MUST cn
-- 	MAY rfc822MailMember )

END
