-- See: https://www.sudo.ws/docs/man/1.8.17/sudoers.ldap.man/
SudoSchema {
    iso(1) identified-organization(3) dod(6) internet(1) private(4)
    enterprise(1) wildboar(56490) module(1) sudo-schema(60)
}
DEFINITIONS
EXPLICIT TAGS
::=
BEGIN

EXPORTS ALL;

IMPORTS

    id-nf
        FROM Wildboar
        {iso(1) identified-organization(3) dod(6) internet(1) private(4)
        enterprise(1) wildboar(56490) module(1) wildboar(1)}
        WITH SUCCESSORS

    ATTRIBUTE, OBJECT-CLASS, top
        FROM InformationFramework
        {joint-iso-itu-t ds(5) module(1) informationFramework(1) 9}
        WITH SUCCESSORS

	description, integer, ia5String, generalizedTime,
    caseExactIA5Match, integerMatch, integerOrderingMatch, commonName,
    generalizedTimeMatch, generalizedTimeOrderingMatch
		FROM SelectedAttributeTypes
		{joint-iso-itu-t ds(5) module(1) selectedAttributeTypes(5) 9}
		WITH SUCCESSORS

    ;

id-aaron-spangler   OBJECT IDENTIFIER ::= { 1 3 6 1 4 1 15953 }

sudoUser ATTRIBUTE ::= {
	WITH SYNTAX                 IA5String
    EQUALITY MATCHING RULE      caseExactIA5Match
    LDAP-SYNTAX                 ia5String.&id
	LDAP-NAME                   { "sudoUser" }
	LDAP-DESC                   "User(s) who may run sudo"
	ID                          { id-aaron-spangler 9 1 1 }
}

sudoHost ATTRIBUTE ::= {
	WITH SYNTAX                 IA5String
    EQUALITY MATCHING RULE      caseExactIA5Match -- REVIEW: I don't think this should be case-sensitive.
    LDAP-SYNTAX                 ia5String.&id
	LDAP-NAME                   { "sudoHost" }
	LDAP-DESC                   "Host(s) who may run sudo"
	ID                          { id-aaron-spangler 9 1 2 }
}

sudoCommand ATTRIBUTE ::= {
	WITH SYNTAX                 IA5String
    EQUALITY MATCHING RULE      caseExactIA5Match
    LDAP-SYNTAX                 ia5String.&id
	LDAP-NAME                   { "sudoCommand" }
	LDAP-DESC                   "Command(s) to be executed by sudo"
	ID                          { id-aaron-spangler 9 1 3 }
}

sudoRunAs ATTRIBUTE ::= {
	WITH SYNTAX                 IA5String
    EQUALITY MATCHING RULE      caseExactIA5Match
    LDAP-SYNTAX                 ia5String.&id
	LDAP-NAME                   { "sudoRunAs" }
	LDAP-DESC                   "User(s) impersonated by sudo"
	ID                          { id-aaron-spangler 9 1 4 }
}

sudoOption ATTRIBUTE ::= {
	WITH SYNTAX                 IA5String
    EQUALITY MATCHING RULE      caseExactIA5Match
    LDAP-SYNTAX                 ia5String.&id
	LDAP-NAME                   { "sudoOption" }
	LDAP-DESC                   "Options(s) followed by sudo"
	ID                          { id-aaron-spangler 9 1 5 }
}

-- REVIEW: It is not clear how this differs from sudoRunAs
sudoRunAsUser ATTRIBUTE ::= {
	WITH SYNTAX                 IA5String
    EQUALITY MATCHING RULE      caseExactIA5Match
    LDAP-SYNTAX                 ia5String.&id
	LDAP-NAME                   { "sudoRunAsUser" }
	LDAP-DESC                   "User(s) impersonated by sudo"
	ID                          { id-aaron-spangler 9 1 6 }
}

sudoRunAsGroup ATTRIBUTE ::= {
	WITH SYNTAX                 IA5String
    EQUALITY MATCHING RULE      caseExactIA5Match
    LDAP-SYNTAX                 ia5String.&id
	LDAP-NAME                   { "sudoRunAsGroup" }
	LDAP-DESC                   "Group(s) impersonated by sudo"
	ID                          { id-aaron-spangler 9 1 7 }
}

-- REVIEW: I believe this should be single-valued.
sudoNotBefore ATTRIBUTE ::= {
	WITH SYNTAX                 GeneralizedTime
    EQUALITY MATCHING RULE      generalizedTimeMatch
    ORDERING MATCHING RULE      generalizedTimeOrderingMatch
    LDAP-SYNTAX                 generalizedTime.&id
	LDAP-NAME                   { "sudoNotBefore" }
	LDAP-DESC                   "Start of time interval for which the entry is valid"
	ID                          { id-aaron-spangler 9 1 8 }
}

-- REVIEW: I believe this should be single-valued.
sudoNotAfter ATTRIBUTE ::= {
	WITH SYNTAX                 GeneralizedTime
    EQUALITY MATCHING RULE      generalizedTimeMatch
    ORDERING MATCHING RULE      generalizedTimeOrderingMatch
    LDAP-SYNTAX                 generalizedTime.&id
	LDAP-NAME                   { "sudoNotAfter" }
	LDAP-DESC                   "End of time interval for which the entry is valid"
	ID                          { id-aaron-spangler 9 1 9 }
}

sudoOrder ATTRIBUTE ::= {
	WITH SYNTAX                 INTEGER (0..MAX)
    EQUALITY MATCHING RULE      integerMatch
    ORDERING MATCHING RULE      integerOrderingMatch
    LDAP-SYNTAX                 integer.&id
	LDAP-NAME                   { "sudoOrder" }
	LDAP-DESC                   "an integer to order the sudoRole entries"
	ID                          { id-aaron-spangler 9 1 10 }
}

sudoRole OBJECT-CLASS ::= {
	SUBCLASS OF         { top }
	KIND                structural
	MUST CONTAIN        { commonName }
    MAY CONTAIN         {
        sudoUser
        | sudoHost
        | sudoCommand
        | sudoRunAs
        | sudoRunAsUser
        | sudoRunAsGroup
        | sudoOption
        | sudoNotBefore
        | sudoNotAfter
        | sudoOrder
        | description
    }
	LDAP-NAME           { "sudoRole" }
	LDAP-DESC           "Sudoer Entries"
	ID                  { id-aaron-spangler 9 2 1 }
}

-- Name Forms

sudoRoleNameForm NAME-FORM ::= {
	NAMES				sudoRole
	WITH ATTRIBUTES		{commonName}
	LDAP-NAME			{"sudoRoleNameForm"}
	ID					{ id-nf 27 }
}

END
