KerberosV5KeyDistributionCenter {
    iso(1) identified-organization(3) dod(6) internet(1) private(4)
    enterprise(1) wildboar(56490) module(1) krb5kdc(42)
}
DEFINITIONS
EXPLICIT TAGS
EXTENSIBILITY IMPLIED
::=
BEGIN

EXPORTS ALL;

IMPORTS

    ATTRIBUTE, OBJECT-CLASS, top, DistinguishedName, distinguishedNameMatch
        FROM InformationFramework
        {joint-iso-itu-t ds(5) module(1) informationFramework(1) 9}
        WITH SUCCESSORS

	ia5String, caseExactIA5Match, distinguishedName, dn, boolean, booleanMatch,
    generalizedTimeMatch, generalizedTime, integer, integerMatch,
    generalizedTimeOrderingMatch, commonName
		FROM SelectedAttributeTypes
		{joint-iso-itu-t ds(5) module(1) selectedAttributeTypes(5) 9}
		WITH SUCCESSORS

    ;

-- Attribute Types

krb5PrincipalName ATTRIBUTE ::= {
	WITH SYNTAX                 IA5String
	EQUALITY MATCHING RULE      caseExactIA5Match
	SINGLE VALUE                TRUE
	USAGE                       userApplications
	LDAP-SYNTAX                 ia5String.&id
	LDAP-NAME                   {"krb5PrincipalName"}
	LDAP-DESC                   "The unparsed Kerberos principal name"
	ID                          { 1 3 6 1 4 1 5322 10 1 1 }
}

krb5Key ATTRIBUTE ::= {
	WITH SYNTAX                 OCTET STRING
	USAGE                       userApplications
	LDAP-SYNTAX                 { 1 3 6 1 4 1 1466 115 121 1 5 }
	LDAP-NAME                   {"krb5Key"}
	LDAP-DESC                   "Encoded ASN1 Key as an octet string"
	ID                          { 1 3 6 1 4 1 5322 10 1 10 }
}

krb5PrincipalRealm ATTRIBUTE ::= {
	SUBTYPE OF                  distinguishedName
	WITH SYNTAX                 DistinguishedName
	EQUALITY MATCHING RULE      distinguishedNameMatch
	USAGE                       userApplications
	LDAP-SYNTAX                 dn.&id
	LDAP-NAME                   {"krb5PrincipalRealm"}
	LDAP-DESC                   "Distinguished name of krb5Realm entry"
	ID                          { 1 3 6 1 4 1 5322 10 1 11 }
}

krb5RealmName ATTRIBUTE ::= {
	WITH SYNTAX                 IA5String
	EQUALITY MATCHING RULE      caseExactIA5Match
	USAGE                       userApplications
	LDAP-SYNTAX                 ia5String.&id
	LDAP-NAME                   {"krb5RealmName"}
	ID                          { 1 3 6 1 4 1 5322 10 1 12 }
}

krb5AccountDisabled ATTRIBUTE ::= {
	WITH SYNTAX                 BOOLEAN
	EQUALITY MATCHING RULE      booleanMatch
	SINGLE VALUE                TRUE
	USAGE                       userApplications
	LDAP-SYNTAX                 boolean.&id
	LDAP-NAME                   {"krb5AccountDisabled"}
	ID                          { 1 3 6 1 4 1 5322 10 1 13 }
}

krb5AccountLockedOut ATTRIBUTE ::= {
	WITH SYNTAX                 BOOLEAN
	EQUALITY MATCHING RULE      booleanMatch
	SINGLE VALUE                TRUE
	USAGE                       userApplications
	LDAP-SYNTAX                 boolean.&id
	LDAP-NAME                   {"krb5AccountLockedOut"}
	ID                          { 1 3 6 1 4 1 5322 10 1 14 }
}

krb5AccountExpirationTime ATTRIBUTE ::= {
	WITH SYNTAX                 GeneralizedTime
	EQUALITY MATCHING RULE      generalizedTimeMatch
	SINGLE VALUE                TRUE
	USAGE                       userApplications
	LDAP-SYNTAX                 generalizedTime.&id
	LDAP-NAME                   {"krb5AccountExpirationTime"}
	ID                          { 1 3 6 1 4 1 5322 10 1 15 }
}

krb5KeyVersionNumber ATTRIBUTE ::= {
	WITH SYNTAX                 INTEGER
	EQUALITY MATCHING RULE      integerMatch
	SINGLE VALUE                TRUE
	USAGE                       userApplications
	LDAP-SYNTAX                 integer.&id
	LDAP-NAME                   {"krb5KeyVersionNumber"}
	ID                          { 1 3 6 1 4 1 5322 10 1 2 }
}

krb5MaxLife ATTRIBUTE ::= {
	WITH SYNTAX                 INTEGER
	EQUALITY MATCHING RULE      integerMatch
	SINGLE VALUE                TRUE
	USAGE                       userApplications
	LDAP-SYNTAX                 integer.&id
	LDAP-NAME                   {"krb5MaxLife"}
	ID                          { 1 3 6 1 4 1 5322 10 1 3 }
}

krb5MaxRenew ATTRIBUTE ::= {
	WITH SYNTAX                 INTEGER
	EQUALITY MATCHING RULE      integerMatch
	SINGLE VALUE                TRUE
	USAGE                       userApplications
	LDAP-SYNTAX                 integer.&id
	LDAP-NAME                   {"krb5MaxRenew"}
	ID                          { 1 3 6 1 4 1 5322 10 1 4 }
}

krb5KDCFlags ATTRIBUTE ::= {
	WITH SYNTAX                 INTEGER
	EQUALITY MATCHING RULE      integerMatch
	SINGLE VALUE                TRUE
	USAGE                       userApplications
	LDAP-SYNTAX                 integer.&id
	LDAP-NAME                   {"krb5KDCFlags"}
	ID                          { 1 3 6 1 4 1 5322 10 1 5 }
}

krb5EncryptionType ATTRIBUTE ::= {
	WITH SYNTAX                 INTEGER
	EQUALITY MATCHING RULE      integerMatch
	USAGE                       userApplications
	LDAP-SYNTAX                 integer.&id
	LDAP-NAME                   {"krb5EncryptionType"}
	ID                          { 1 3 6 1 4 1 5322 10 1 6 }
}

krb5ValidStart ATTRIBUTE ::= {
	WITH SYNTAX                 GeneralizedTime
	EQUALITY MATCHING RULE      generalizedTimeMatch
	ORDERING MATCHING RULE      generalizedTimeOrderingMatch
	SINGLE VALUE                TRUE
	USAGE                       userApplications
	LDAP-SYNTAX                 generalizedTime.&id
	LDAP-NAME                   {"krb5ValidStart"}
	ID                          { 1 3 6 1 4 1 5322 10 1 7 }
}

krb5ValidEnd ATTRIBUTE ::= {
	WITH SYNTAX                 GeneralizedTime
	EQUALITY MATCHING RULE      generalizedTimeMatch
	ORDERING MATCHING RULE      generalizedTimeOrderingMatch
	SINGLE VALUE                TRUE
	USAGE                       userApplications
	LDAP-SYNTAX                 generalizedTime.&id
	LDAP-NAME                   {"krb5ValidEnd"}
	ID                          { 1 3 6 1 4 1 5322 10 1 8 }
}

krb5PasswordEnd ATTRIBUTE ::= {
	WITH SYNTAX                 GeneralizedTime
	EQUALITY MATCHING RULE      generalizedTimeMatch
	ORDERING MATCHING RULE      generalizedTimeOrderingMatch
	SINGLE VALUE                TRUE
	USAGE                       userApplications
	LDAP-SYNTAX                 generalizedTime.&id
	LDAP-NAME                   {"krb5PasswordEnd"}
	ID                          { 1 3 6 1 4 1 5322 10 1 9 }
}

-- Object Classes

krb5Principal OBJECT-CLASS ::= {
	SUBCLASS OF     {top}
	KIND            auxiliary
	MUST CONTAIN    {krb5PrincipalName}
	MAY CONTAIN     {commonName | krb5PrincipalRealm}
	LDAP-NAME       {"krb5Principal"}
	ID              { 1 3 6 1 4 1 5322 10 2 1 }
}

krb5KDCEntry OBJECT-CLASS ::= {
	SUBCLASS OF     {krb5Principal}
	KIND            auxiliary
	MUST CONTAIN    {krb5KeyVersionNumber}
	MAY CONTAIN     {
        krb5ValidStart
        | krb5ValidEnd
        | krb5PasswordEnd
        | krb5MaxLife
        | krb5MaxRenew
        | krb5KDCFlags
        | krb5EncryptionType
        | krb5Key
        | krb5AccountDisabled
        | krb5AccountLockedOut
        | krb5AccountExpirationTime
    }
	LDAP-NAME       {"krb5KDCEntry"}
	ID              { 1 3 6 1 4 1 5322 10 2 2 }
}

krb5Realm OBJECT-CLASS ::= {
	SUBCLASS OF     {top}
	KIND            auxiliary
	MUST CONTAIN    {krb5RealmName}
	LDAP-NAME       {"krb5Realm"}
	ID              { 1 3 6 1 4 1 5322 10 2 3 }
}

END
