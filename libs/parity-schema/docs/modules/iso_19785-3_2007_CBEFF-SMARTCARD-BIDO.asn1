-- Module CBEFF-SMARTCARD-BIDO (ISO/IEC 19785-3:2007)
--
-- Copyright © ISO/IEC 2007. This version of
-- this ASN.1 module is part of ISO/IEC 10031-2:2007;
-- see the ISO|IEC text itself for full legal notices.
--
CBEFF-SMARTCARD-BIDO
 -- The abbreviation BIDO is used for Biometric Information Data Object
  {iso standard 19785 modules(0) types-for-smartcard(8)} DEFINITIONS IMPLICIT
TAGS ::=
BEGIN

-- In all cases, omission of an optional component that represents a
-- CBEFF data element is the encoding of the NO VALUE AVAILABLE for
-- that data element.
PatronHeaderVersion ::= OCTET STRING(SIZE (2))

-- CBEFF_patron_header_version
-- The first octet encodes the major version number
-- The second octet encodes the minor version number
BiometricType ::= OCTET STRING(SIZE (1..3))

-- CBEFF_BDB_biometric_type
-- The encoding of the abstract values in the value part of the
-- TLV shall be the Recommended Encodings specified in Table 11.5.
-- Note that this is different from the encoding of this type in
-- clause 29.10 and in other patron formats specified in this part of
-- ISO/IEC 19785.
BiometricSubType ::= OCTET STRING(SIZE (1))

-- CBEFF_BDB_biometric_subtype
-- The encoding of the abstract values in the value part of the
-- TLV shall be the Recommended Encodings specified in Table 11.6.
-- Note that this is different from the encoding of this type in
-- Table A.2 and in other patron formats specified in this part of
-- ISO/IEC 19785.
BCDTime ::= OCTET STRING(SIZE (7))

-- BCD encoded timestamp with format ' YYYYMMDDHHMMSS'
Creator ::= UTF8String

-- CBEFF_BIR_creator
BCDDate ::= OCTET STRING(SIZE (4))

-- BCD encoded date with format 'YYYYMMDD'
BCDDatePeriod ::= OCTET STRING(SIZE (8))

-- Two concatenated BCD encoded dates with format YYYYMMDDYYYYMMDD
ProductID ::= OCTET STRING(SIZE (4))

-- CBEFF_BDB_product_owner in the first two octets
-- CBEFF_BDB_product_type in the last two octets
FormatOwner ::= OCTET STRING(SIZE (2))

-- CBEFF_BDB_format_owner
FormatType ::= OCTET STRING(SIZE (2))

-- CBEFF_BDB_format_type
BIRIndex ::= OCTET STRING

-- CBEFF_BIR_index
BiometricInformationTemplate ::= [APPLICATION 96]  SET {
  algorithmReference       [0]  OCTET STRING(SIZE (1)) OPTIONAL,
  -- A non-CBEFF data element &#8211; see ISO/IEC 7816-11
  referenceDataQualifier   [3]  OCTET STRING(SIZE (1)) OPTIONAL,
  -- A non-CBEFF data element &#8211; see ISO/IEC 7816-11
  biometricHeaderTemplate  [1]  BiometricHeaderTemplate,
  bdbReferenceData         [APPLICATION 46]  EXTERNAL OPTIONAL,
  -- A CBEFF BDB, mandatory for off-card-matching
  birPayLoad               [APPLICATION 19]  OCTET STRING OPTIONAL
  -- CBEFF_BIR_payload, contents defined by ISO/IEC 7816-11
}

GroupBIT ::= [APPLICATION 97]  SET OF BiometricInformationTemplate

BiometricHeaderTemplate ::= SET {
  patronHeaderVersion    [0]  PatronHeaderVersion DEFAULT '0101'H,
  -- The absence of this Data Object represents NO VALUE AVAILABLE
  bdbBiometricType       [1]  BiometricType OPTIONAL,
  bdbBiometricSubType    [2]  BiometricSubType OPTIONAL,
  -- Required to be absent unless bdbBiometricType is present
  bdbCreationDate        [3]  BCDTime OPTIONAL,
  -- CBEFF_BDB_creation_date
  birCreator             [4]  Creator OPTIONAL,
  bdbValidityPeriod      [5]  BCDDatePeriod OPTIONAL,
  bdbPID                 [6]  ProductID OPTIONAL,
  bdbFormatOwner         [7]  FormatOwner,
  bdbFormatType          [8]  FormatType,
  birIndex               [16]  BIRIndex OPTIONAL,
  matchingAlgParameters  [17]  OCTET STRING OPTIONAL
  -- A non-CBEFF data element &#8211; see ISO/IEC 7816-11
}

END

-- Generated by Asnp, the ASN.1 pretty-printer of France Telecom R&D
