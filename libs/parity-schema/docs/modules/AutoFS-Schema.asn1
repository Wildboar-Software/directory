AutoFS-Schema {
    iso(1) identified-organization(3) dod(6) internet(1) private(4)
    enterprise(1) wildboar(56490) module(1) auto-fs-schema(40)
}
DEFINITIONS
EXPLICIT TAGS
EXTENSIBILITY IMPLIED
::=
BEGIN

EXPORTS ALL;

IMPORTS

    id-nf
        FROM Wildboar
        {iso(1) identified-organization(3) dod(6) internet(1) private(4)
        enterprise(1) wildboar(56490) module(1) wildboar(1)}
        WITH SUCCESSORS

    ATTRIBUTE, OBJECT-CLASS, top
        FROM InformationFramework
        {joint-iso-itu-t ds(5) module(1) informationFramework(1) 9}
        WITH SUCCESSORS

	directoryString, ia5String, uid, commonName, organizationalUnitName,
    description
		FROM SelectedAttributeTypes
		{joint-iso-itu-t ds(5) module(1) selectedAttributeTypes(5) 9}
		WITH SUCCESSORS

    ;

-- Attribute Types

automountInformation ATTRIBUTE ::= {
	WITH SYNTAX                 IA5String
	EQUALITY MATCHING RULE      caseExactMatch
	SINGLE VALUE                TRUE
	USAGE                       userApplications
	LDAP-SYNTAX                 ia5String.&id
	LDAP-NAME                   {"automountInformation"}
	LDAP-DESC                   "Information used by the autofs automounter"
	ID                          { 1 3 6 1 4 1 2312 4 1 2 }
}

-- Object Classes

automountMap OBJECT-CLASS ::= {
	SUBCLASS OF     {top}
	KIND            structural
	MUST CONTAIN    {organizationalUnitName}
	LDAP-NAME       {"automountMap"}
	LDAP-DESC       "An group of related automount objects"
	ID              { 1 3 6 1 4 1 2312 4 2 2 }
}

automount OBJECT-CLASS ::= {
	SUBCLASS OF     {top}
	KIND            structural
	MUST CONTAIN    {commonName | automountInformation}
	MAY CONTAIN     {description}
	LDAP-NAME       {"automount"}
	LDAP-DESC       "An entry in an automounter map"
	ID              { 1 3 6 1 4 1 2312 4 2 3 }
}

-- Name Forms

automountMapNameForm NAME-FORM ::= {
	NAMES				automountMap
	WITH ATTRIBUTES		{organizationalUnitName}
	LDAP-NAME			{"automountMapNameForm"}
	ID					{ id-nf 28 }
}

automountNameForm NAME-FORM ::= {
	NAMES				automount
	WITH ATTRIBUTES		{commonName}
	LDAP-NAME			{"automountNameForm"}
	ID					{ id-nf 29 }
}

END
