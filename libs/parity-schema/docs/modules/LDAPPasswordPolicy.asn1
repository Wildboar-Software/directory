-- See: https://datatracker.ietf.org/doc/html/draft-behera-ldap-password-policy-10
LDAPPasswordPolicy {
    iso(1) identified-organization(3) dod(6) internet(1) private(4)
    enterprise(1) wildboar(56490) module(1) ldap-ppolicy(34)
}
DEFINITIONS
EXPLICIT TAGS
EXTENSIBILITY IMPLIED
::=
BEGIN

EXPORTS ALL;

IMPORTS

    ATTRIBUTE, DistinguishedName, distinguishedNameMatch, objectIdentifierMatch, top
        FROM InformationFramework
        {joint-iso-itu-t ds(5) module(1) informationFramework(1) 9}
        WITH SUCCESSORS

    dn, oid, integer, boolean, booleanMatch, integerMatch, integerOrderingMatch,
    generalizedTime, generalizedTimeMatch, generalizedTimeOrderingMatch,
    octetString, octetStringMatch, octetStringOrderingMatch, octetStringSubstringsMatch
		FROM SelectedAttributeTypes
		{joint-iso-itu-t ds(5) module(1) selectedAttributeTypes(5) 9}
		WITH SUCCESSORS

    ;

-- Object Identifiers

id-ppolicy                      OBJECT IDENTIFIER ::= { 1 3 6 1 4 1 42 2 27 8 }
id-ppolicy-at                   OBJECT IDENTIFIER ::= { id-ppolicy 1 }
id-ppolicy-oc                   OBJECT IDENTIFIER ::= { id-ppolicy 2 }
id-ppolicy-control              OBJECT IDENTIFIER ::= { id-ppolicy 5 }
id-at-pwdAttribute              OBJECT IDENTIFIER ::= { id-ppolicy-at 1 }
id-at-pwdMinAge                 OBJECT IDENTIFIER ::= { id-ppolicy-at 2 }
id-at-pwdMaxAge                 OBJECT IDENTIFIER ::= { id-ppolicy-at 3 }
id-at-pwdInHistory              OBJECT IDENTIFIER ::= { id-ppolicy-at 4 }
id-at-pwdCheckQuality           OBJECT IDENTIFIER ::= { id-ppolicy-at 5 }
id-at-pwdMinLength              OBJECT IDENTIFIER ::= { id-ppolicy-at 6 }
id-at-pwdExpireWarning          OBJECT IDENTIFIER ::= { id-ppolicy-at 7 }
id-at-pwdGraceAuthNLimit        OBJECT IDENTIFIER ::= { id-ppolicy-at 8 }
id-at-pwdLockout                OBJECT IDENTIFIER ::= { id-ppolicy-at 9 }
id-at-pwdLockoutDuration        OBJECT IDENTIFIER ::= { id-ppolicy-at 10 }
id-at-pwdMaxFailure             OBJECT IDENTIFIER ::= { id-ppolicy-at 11 }
id-at-pwdFailureCountInterval   OBJECT IDENTIFIER ::= { id-ppolicy-at 12 }
id-at-pwdMustChange             OBJECT IDENTIFIER ::= { id-ppolicy-at 13 }
id-at-pwdAllowUserChange        OBJECT IDENTIFIER ::= { id-ppolicy-at 14 }
id-at-pwdSafeModify             OBJECT IDENTIFIER ::= { id-ppolicy-at 15 }
id-at-pwdChangedTime            OBJECT IDENTIFIER ::= { id-ppolicy-at 16 }
id-at-pwdAccountLockedTime      OBJECT IDENTIFIER ::= { id-ppolicy-at 17 }
id-at-pwdFailureTime            OBJECT IDENTIFIER ::= { id-ppolicy-at 19 }
id-at-pwdHistory                OBJECT IDENTIFIER ::= { id-ppolicy-at 20 }
id-at-pwdGraceUseTime           OBJECT IDENTIFIER ::= { id-ppolicy-at 21 }
id-at-pwdReset                  OBJECT IDENTIFIER ::= { id-ppolicy-at 22 }
id-at-pwdPolicySubentry         OBJECT IDENTIFIER ::= { id-ppolicy-at 23 }
id-at-pwdMinDelay               OBJECT IDENTIFIER ::= { id-ppolicy-at 24 }
id-at-pwdMaxDelay               OBJECT IDENTIFIER ::= { id-ppolicy-at 25 }
id-at-pwdMaxIdle                OBJECT IDENTIFIER ::= { id-ppolicy-at 26 }
id-at-pwdStartTime              OBJECT IDENTIFIER ::= { id-ppolicy-at 27 }
id-at-pwdEndTime                OBJECT IDENTIFIER ::= { id-ppolicy-at 28 }
id-at-pwdLastSuccess            OBJECT IDENTIFIER ::= { id-ppolicy-at 29 }
id-at-pwdGraceExpire            OBJECT IDENTIFIER ::= { id-ppolicy-at 30 }
id-at-pwdMaxLength              OBJECT IDENTIFIER ::= { id-ppolicy-at 31 }
id-oc-pwdPolicy                 OBJECT IDENTIFIER ::= { id-ppolicy-oc 1 }
id-control-ppolicy              OBJECT IDENTIFIER ::= { id-ppolicy-control 1 }

-- Attribute Types

pwdAttribute ATTRIBUTE ::= {
    WITH SYNTAX 				OBJECT IDENTIFIER
    EQUALITY MATCHING RULE 		objectIdentifierMatch
	LDAP-SYNTAX 				oid.&id
	LDAP-NAME 					{"pwdAttribute"}
    ID                          id-at-pwdAttribute
}

pwdMinAge ATTRIBUTE ::= {
    WITH SYNTAX 				INTEGER (0..MAX)
    EQUALITY MATCHING RULE 		integerMatch
    SINGLE VALUE                TRUE
	LDAP-SYNTAX 				integer.&id
	LDAP-NAME 					{"pwdMinAge"}
    ID                          id-at-pwdMinAge
}

pwdMaxAge ATTRIBUTE ::= {
    WITH SYNTAX 				INTEGER (0..MAX)
    EQUALITY MATCHING RULE 		integerMatch
    SINGLE VALUE                TRUE
	LDAP-SYNTAX 				integer.&id
	LDAP-NAME 					{"pwdMaxAge"}
    ID                          id-at-pwdMaxAge
}

pwdInHistory ATTRIBUTE ::= {
    WITH SYNTAX 				INTEGER (0..MAX)
    EQUALITY MATCHING RULE 		integerMatch
    SINGLE VALUE                TRUE
	LDAP-SYNTAX 				integer.&id
	LDAP-NAME 					{"pwdInHistory"}
    ID                          id-at-pwdInHistory
}

pwdCheckQuality ATTRIBUTE ::= {
    WITH SYNTAX 				INTEGER (0..MAX)
    EQUALITY MATCHING RULE 		integerMatch
    SINGLE VALUE                TRUE
	LDAP-SYNTAX 				integer.&id
	LDAP-NAME 					{"pwdCheckQuality"}
    ID                          id-at-pwdCheckQuality
}

pwdMinLength ATTRIBUTE ::= {
    WITH SYNTAX 				INTEGER (0..MAX)
    EQUALITY MATCHING RULE 		integerMatch
    SINGLE VALUE                TRUE
	LDAP-SYNTAX 				integer.&id
	LDAP-NAME 					{"pwdMinLength"}
    ID                          id-at-pwdMinLength
}

pwdMaxLength ATTRIBUTE ::= {
    WITH SYNTAX 				INTEGER (0..MAX)
    EQUALITY MATCHING RULE 		integerMatch
    SINGLE VALUE                TRUE
	LDAP-SYNTAX 				integer.&id
	LDAP-NAME 					{"pwdMaxLength"}
    ID                          id-at-pwdMaxLength
}

pwdExpireWarning ATTRIBUTE ::= {
    WITH SYNTAX 				INTEGER (0..MAX)
    EQUALITY MATCHING RULE 		integerMatch
    SINGLE VALUE                TRUE
	LDAP-SYNTAX 				integer.&id
	LDAP-NAME 					{"pwdExpireWarning"}
    ID                          id-at-pwdExpireWarning
}

-- Basically the same as pwdGraces
pwdGraceAuthNLimit ATTRIBUTE ::= {
    WITH SYNTAX 				INTEGER (0..MAX)
    EQUALITY MATCHING RULE 		integerMatch
    SINGLE VALUE                TRUE
	LDAP-SYNTAX 				integer.&id
	LDAP-NAME 					{"pwdGraceAuthNLimit"}
    ID                          id-at-pwdGraceAuthNLimit
}

pwdGraceExpire ATTRIBUTE ::= {
    WITH SYNTAX 				INTEGER (0..MAX)
    EQUALITY MATCHING RULE 		integerMatch
    SINGLE VALUE                TRUE
	LDAP-SYNTAX 				integer.&id
	LDAP-NAME 					{"pwdGraceExpire"}
    ID                          id-at-pwdGraceExpire
}

pwdLockout ATTRIBUTE ::= {
    WITH SYNTAX 				BOOLEAN
    EQUALITY MATCHING RULE 		booleanMatch
    SINGLE VALUE                TRUE
	LDAP-SYNTAX 				boolean.&id
	LDAP-NAME 					{"pwdLockout"}
    ID                          id-at-pwdLockout
}

pwdLockoutDuration ATTRIBUTE ::= {
    WITH SYNTAX 				INTEGER (0..MAX)
    EQUALITY MATCHING RULE 		integerMatch
    SINGLE VALUE                TRUE
	LDAP-SYNTAX 				integer.&id
	LDAP-NAME 					{"pwdLockoutDuration"}
    ID                          id-at-pwdLockoutDuration
}

pwdMaxFailure ATTRIBUTE ::= {
    WITH SYNTAX 				INTEGER (0..MAX)
    EQUALITY MATCHING RULE 		integerMatch
    SINGLE VALUE                TRUE
	LDAP-SYNTAX 				integer.&id
	LDAP-NAME 					{"pwdMaxFailure"}
    ID                          id-at-pwdMaxFailure
}

pwdFailureCountInterval ATTRIBUTE ::= {
    WITH SYNTAX 				INTEGER (0..MAX)
    EQUALITY MATCHING RULE 		integerMatch
    SINGLE VALUE                TRUE
	LDAP-SYNTAX 				integer.&id
	LDAP-NAME 					{"pwdFailureCountInterval"}
    ID                          id-at-pwdFailureCountInterval
}

pwdMustChange ATTRIBUTE ::= {
    WITH SYNTAX 				BOOLEAN
    EQUALITY MATCHING RULE 		booleanMatch
    SINGLE VALUE                TRUE
	LDAP-SYNTAX 				boolean.&id
	LDAP-NAME 					{"pwdMustChange"}
    ID                          id-at-pwdMustChange
}

pwdAllowUserChange ATTRIBUTE ::= {
    WITH SYNTAX 				BOOLEAN
    EQUALITY MATCHING RULE 		booleanMatch
    SINGLE VALUE                TRUE
	LDAP-SYNTAX 				boolean.&id
	LDAP-NAME 					{"pwdAllowUserChange"}
    ID                          id-at-pwdAllowUserChange
}

pwdSafeModify ATTRIBUTE ::= {
    WITH SYNTAX 				BOOLEAN
    EQUALITY MATCHING RULE 		booleanMatch
    SINGLE VALUE                TRUE
	LDAP-SYNTAX 				boolean.&id
	LDAP-NAME 					{"pwdSafeModify"}
    ID                          id-at-pwdSafeModify
}

pwdMinDelay ATTRIBUTE ::= {
    WITH SYNTAX 				INTEGER (0..MAX)
    EQUALITY MATCHING RULE 		integerMatch
    SINGLE VALUE                TRUE
	LDAP-SYNTAX 				integer.&id
	LDAP-NAME 					{"pwdMinDelay"}
    ID                          id-at-pwdMinDelay
}

pwdMaxDelay ATTRIBUTE ::= {
    WITH SYNTAX 				INTEGER (0..MAX)
    EQUALITY MATCHING RULE 		integerMatch
    SINGLE VALUE                TRUE
	LDAP-SYNTAX 				integer.&id
	LDAP-NAME 					{"pwdMaxDelay"}
    ID                          id-at-pwdMaxDelay
}

pwdMaxIdle ATTRIBUTE ::= {
    WITH SYNTAX 				INTEGER (0..MAX)
    EQUALITY MATCHING RULE 		integerMatch
    SINGLE VALUE                TRUE
	LDAP-SYNTAX 				integer.&id
	LDAP-NAME 					{"pwdMaxIdle"}
    ID                          id-at-pwdMaxIdle
}

pwdChangedTime ATTRIBUTE ::= {
    WITH SYNTAX 				GeneralizedTime
    EQUALITY MATCHING RULE 		generalizedTimeMatch
    ORDERING MATCHING RULE      generalizedTimeOrderingMatch
    SINGLE VALUE                TRUE
    NO USER MODIFICATION        TRUE
    USAGE                       directoryOperation
	LDAP-SYNTAX 				generalizedTime.&id
	LDAP-NAME 					{"pwdChangedTime"}
    LDAP-DESC                   "The time the password was last changed"
    ID                          id-at-pwdChangedTime
}

pwdAccountLockedTime ATTRIBUTE ::= {
    WITH SYNTAX 				GeneralizedTime
    EQUALITY MATCHING RULE 		generalizedTimeMatch
    ORDERING MATCHING RULE      generalizedTimeOrderingMatch
    SINGLE VALUE                TRUE
    NO USER MODIFICATION        TRUE
    USAGE                       directoryOperation
	LDAP-SYNTAX 				generalizedTime.&id
	LDAP-NAME 					{"pwdAccountLockedTime"}
    LDAP-DESC                   "The time an user account was locked"
    ID                          id-at-pwdAccountLockedTime
}

pwdFailureTime ATTRIBUTE ::= {
    WITH SYNTAX 				GeneralizedTime
    EQUALITY MATCHING RULE 		generalizedTimeMatch
    ORDERING MATCHING RULE      generalizedTimeOrderingMatch
    SINGLE VALUE                TRUE
    NO USER MODIFICATION        TRUE
    USAGE                       directoryOperation
	LDAP-SYNTAX 				generalizedTime.&id
	LDAP-NAME 					{"pwdFailureTime"}
    LDAP-DESC                   "The timestamps of the last consecutive authentication failures"
    ID                          id-at-pwdFailureTime
}

pwdHistory ATTRIBUTE ::= {
    WITH SYNTAX 				OCTET STRING
    EQUALITY MATCHING RULE 		octetStringMatch
    ORDERING MATCHING RULE      octetStringOrderingMatch
    SUBSTRINGS MATCHING RULE    octetStringSubstringsMatch
    NO USER MODIFICATION        TRUE
    USAGE                       directoryOperation
	LDAP-SYNTAX 				octetString.&id
	LDAP-NAME 					{"pwdHistory"}
    LDAP-DESC                   "The history of user s passwords"
    ID                          id-at-pwdHistory
}

pwdGraceUseTime ATTRIBUTE ::= {
    WITH SYNTAX 				GeneralizedTime
    EQUALITY MATCHING RULE 		generalizedTimeMatch
    ORDERING MATCHING RULE      generalizedTimeOrderingMatch
    NO USER MODIFICATION        TRUE
    USAGE                       directoryOperation
	LDAP-SYNTAX 				generalizedTime.&id
	LDAP-NAME 					{"pwdGraceUseTime"}
    LDAP-DESC                   "The timestamps of the grace authentication after the password has expired"
    ID                          id-at-pwdGraceUseTime
}

pwdReset ATTRIBUTE ::= {
    WITH SYNTAX 				BOOLEAN
    EQUALITY MATCHING RULE 		booleanMatch
    SINGLE VALUE                TRUE
	LDAP-SYNTAX 				boolean.&id
	LDAP-NAME 					{"pwdReset"}
    LDAP-DESC                   "The indication that the password has been reset"
    ID                          id-at-pwdReset
}

pwdPolicySubentry ATTRIBUTE ::= {
    WITH SYNTAX 				DistinguishedName
    EQUALITY MATCHING RULE 		distinguishedNameMatch
    SINGLE VALUE                TRUE
    NO USER MODIFICATION        TRUE
    USAGE                       directoryOperation
	LDAP-SYNTAX 				dn.&id
	LDAP-NAME 					{"pwdPolicySubentry"}
    LDAP-DESC                   "The pwdPolicy subentry in effect for this object"
    ID                          id-at-pwdPolicySubentry
}

pwdStartTime ATTRIBUTE ::= {
    WITH SYNTAX 				GeneralizedTime
    EQUALITY MATCHING RULE 		generalizedTimeMatch
    ORDERING MATCHING RULE      generalizedTimeOrderingMatch
    SINGLE VALUE                TRUE
    NO USER MODIFICATION        TRUE
    USAGE                       directoryOperation
	LDAP-SYNTAX 				generalizedTime.&id
	LDAP-NAME 					{"pwdStartTime"}
    LDAP-DESC                   "The time the password becomes enabled"
    ID                          id-at-pwdStartTime
}

pwdEndTime ATTRIBUTE ::= {
    WITH SYNTAX 				GeneralizedTime
    EQUALITY MATCHING RULE 		generalizedTimeMatch
    ORDERING MATCHING RULE      generalizedTimeOrderingMatch
    SINGLE VALUE                TRUE
    NO USER MODIFICATION        TRUE
    USAGE                       directoryOperation
	LDAP-SYNTAX 				generalizedTime.&id
	LDAP-NAME 					{"pwdEndTime"}
    LDAP-DESC                   "The time the password becomes disabled"
    ID                          id-at-pwdEndTime
}

pwdLastSuccess ATTRIBUTE ::= {
    WITH SYNTAX 				GeneralizedTime
    EQUALITY MATCHING RULE 		generalizedTimeMatch
    ORDERING MATCHING RULE      generalizedTimeOrderingMatch
    SINGLE VALUE                TRUE
    NO USER MODIFICATION        TRUE
    USAGE                       directoryOperation
	LDAP-SYNTAX 				generalizedTime.&id
	LDAP-NAME 					{"pwdLastSuccess"}
    LDAP-DESC                   "The timestamp of the last successful authentication"
    ID                          id-at-pwdLastSuccess
}

-- Object Classes

pwdPolicy OBJECT-CLASS ::= {
    SUBCLASS OF     {top}
    KIND            auxiliary
    MUST CONTAIN    {pwdAttribute}
    MAY CONTAIN     {
        pwdMinAge
        | pwdMaxAge
        | pwdInHistory
        | pwdCheckQuality
        | pwdMinLength
        | pwdMaxLength
        | pwdExpireWarning
        | pwdGraceAuthNLimit
        | pwdGraceExpiry
        | pwdLockout
        | pwdLockoutDuration
        | pwdMaxFailure
        | pwdFailureCountInterval
        | pwdMustChange
        | pwdAllowUserChange
        | pwdSafeModify
        | pwdMinDelay
        | pwdMaxDelay
        | pwdMaxIdle
    }
    LDAP-NAME       {"pwdPolicy"}
    ID              id-oc-pwdPolicy
}

-- LDAP Controls

PasswordPolicyResponseValue ::= SEQUENCE {
    warning [0] CHOICE {
        timeBeforeExpiration [0] INTEGER (0 .. maxInt),
        graceAuthNsRemaining [1] INTEGER (0 .. maxInt) } OPTIONAL,
    error   [1] ENUMERATED {
        passwordExpired             (0),
        accountLocked               (1),
        changeAfterReset            (2),
        passwordModNotAllowed       (3),
        mustSupplyOldPassword       (4),
        insufficientPasswordQuality (5),
        passwordTooShort            (6),
        passwordTooYoung            (7),
        passwordInHistory           (8) } OPTIONAL }

END
