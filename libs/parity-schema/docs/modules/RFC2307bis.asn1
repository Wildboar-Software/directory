RFC2307bis {
    iso(1) identified-organization(3) dod(6) internet(1) private(4)
    enterprise(1) wildboar(56490) module(1) rfc2307-bis(44)
}
DEFINITIONS
EXPLICIT TAGS
EXTENSIBILITY IMPLIED
::=
BEGIN

EXPORTS ALL;

IMPORTS

    ATTRIBUTE, OBJECT-CLASS, top
        FROM InformationFramework
        {joint-iso-itu-t ds(5) module(1) informationFramework(1) 9}
        WITH SUCCESSORS

	octetStringMatch, octetString, caseIgnoreIA5Match, ia5String,
    caseExactIA5Match, caseExactIA5SubstringsMatch, commonName,
    description
		FROM SelectedAttributeTypes
		{joint-iso-itu-t ds(5) module(1) selectedAttributeTypes(5) 9}
		WITH SUCCESSORS

    uidNumber
        FROM NIS
        {iso(1) identified-organization(3) dod(6) internet(1) private(4)
        enterprise(1) wildboar(56490) module(1) nis(7)}

    ;

nisPublicKey ATTRIBUTE ::= {
	WITH SYNTAX                 OCTET STRING
	EQUALITY MATCHING RULE      octetStringMatch
	SINGLE VALUE                TRUE
	LDAP-SYNTAX                 octetString.&id
	LDAP-NAME                   {"nisPublicKey"}
	LDAP-DESC                   "NIS public key"
	ID                          { 1 3 6 1 1 1 1 28 }
}

nisSecretKey ATTRIBUTE ::= {
	WITH SYNTAX                 OCTET STRING
	EQUALITY MATCHING RULE      octetStringMatch
	SINGLE VALUE                TRUE
	LDAP-SYNTAX                 octetString.&id
	LDAP-NAME                   {"nisSecretKey"}
	LDAP-DESC                   "NIS secret key"
	ID                          { 1 3 6 1 1 1 1 29 }
}

nisDomain ATTRIBUTE ::= {
	WITH SYNTAX                 IA5String
	EQUALITY MATCHING RULE      caseIgnoreIA5Match
	LDAP-SYNTAX                 ia5String.&id
	LDAP-NAME                   {"nisDomain"}
	LDAP-DESC                   "NIS domain"
	ID                          { 1 3 6 1 1 1 1 30 }
}

automountMapName ATTRIBUTE ::= {
	WITH SYNTAX                 IA5String
	EQUALITY MATCHING RULE      caseExactIA5Match
	SUBSTRINGS MATCHING RULE    caseExactIA5SubstringsMatch
	SINGLE VALUE                TRUE
	LDAP-SYNTAX                 ia5String.&id
	LDAP-NAME                   {"automountMapName"}
	LDAP-DESC                   "automount Map Name"
	ID                          { 1 3 6 1 1 1 1 31 }
}

automountKey ATTRIBUTE ::= {
	WITH SYNTAX                 IA5String
	EQUALITY MATCHING RULE      caseExactIA5Match
	SUBSTRINGS MATCHING RULE    caseExactIA5SubstringsMatch
	SINGLE VALUE                TRUE
	LDAP-SYNTAX                 ia5String.&id
	LDAP-NAME                   {"automountKey"}
	LDAP-DESC                   "Automount Key value"
	ID                          { 1 3 6 1 1 1 1 32 }
}

nisKeyObject OBJECT-CLASS ::= {
	SUBCLASS OF     {top}
	KIND            auxiliary
	MUST CONTAIN    {commonName | nisPublicKey | nisSecretKey}
	MAY CONTAIN     {uidNumber | description}
	LDAP-NAME       {"nisKeyObject"}
	LDAP-DESC       "An object with a public and secret key"
	ID              { 1 3 6 1 1 1 2 14 }
}

nisDomainObject OBJECT-CLASS ::= {
	SUBCLASS OF     {top}
	KIND            auxiliary
	MUST CONTAIN    {nisDomain}
	LDAP-NAME       {"nisDomainObject"}
	LDAP-DESC       "Associates a NIS domain with a naming context"
	ID              { 1 3 6 1 1 1 2 15 }
}

-- Commented out because namedObject is defined by OpenLDAP with more optional attributes.
-- namedObject OBJECT-CLASS ::= {
-- 	SUBCLASS OF     {top}
-- 	MAY CONTAIN     {commonName}
-- 	LDAP-NAME       {"namedObject"}
-- 	ID              { 1 3 6 1 4 1 5322 13 1 1 }
-- }

END
