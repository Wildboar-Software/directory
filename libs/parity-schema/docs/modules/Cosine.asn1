Cosine {
    iso(1) identified-organization(3) dod(6) internet(1) private(4)
    enterprise(1) wildboar(56490) module(1) cosine(3)
}
DEFINITIONS
EXPLICIT TAGS
EXTENSIBILITY IMPLIED
::=
BEGIN

EXPORTS ALL;

IMPORTS

    id-nf
        FROM Wildboar
        {iso(1) identified-organization(3) dod(6) internet(1) private(4)
        enterprise(1) wildboar(56490) module(1) wildboar(1)}
        WITH SUCCESSORS

    ATTRIBUTE, MATCHING-RULE, OBJECT-CLASS, NAME-FORM, DistinguishedName, top,
    distinguishedNameMatch
        FROM InformationFramework
        {joint-iso-itu-t ds(5) module(1) informationFramework(1) 9}
        WITH SUCCESSORS

	directoryString, dn, telephoneNumberMatch, telephoneNr, TelephoneNumber,
	caseIgnoreIA5Match, caseIgnoreIA5SubstringsMatch, ia5String,
	caseIgnoreListMatch, caseIgnoreListSubstringsMatch, postalAddr,
	PostalAddress, caseIgnoreMatch, caseIgnoreOrderingMatch,
	caseIgnoreSubstringsMatch, octetString, preferredDeliveryMethod,
	businessCategory, description, seeAlso, localityName, organizationName,
	organizationalUnitName, commonName, telephoneNumber, dc, searchGuide,
	stateOrProvinceName, physicalDeliveryOfficeName, postalAddress, postalCode,
	postOfficeBox, streetAddress, facsimileTelephoneNumber, telexNumber,
	internationalISDNNumber, destinationIndicator, registeredAddress,
	x121Address, surname, uid, DirectoryString, telephoneNumberSubstringsMatch,
    caseExactIA5Match, countryName
		FROM SelectedAttributeTypes
		{joint-iso-itu-t ds(5) module(1) selectedAttributeTypes(5) 9}
		WITH SUCCESSORS

	person, country, organization, organizationalUnit
		FROM SelectedObjectClasses
		{joint-iso-itu-t ds(5) module(1) selectedObjectClasses(6) 9}
		WITH SUCCESSORS

	userPassword
		FROM AuthenticationFramework
		{joint-iso-itu-t ds(5) module(1) authenticationFramework(7) 9}
		WITH SUCCESSORS
    ;

pilotAttributeType OBJECT IDENTIFIER ::= {
	itu-t(0)
	data(9)
	pss(2342)
	ucl(19200300)
	pilot(100)
	pilotAttributeType(1)
}

pilotObjectClass OBJECT IDENTIFIER ::= {
	itu-t(0)
	data(9)
	pss(2342)
	ucl(19200300)
	pilot(100)
	pilotAttributeType(4)
}

ldapSyntax OBJECT IDENTIFIER ::= {
	iso(1)
	identified-organization(3)
	dod(6)
	internet(1)
	private(4)
	enterprise(1)
	1466
	115
	121
	ldap-syntax(1)
}

-- 9.3.2.  Text Encoded O/R Address
--
--  The Text Encoded O/R Address attribute type specifies a text encoding
--  of an X.400 O/R address, as specified in RFC 987.  The use of this
--  attribute is deprecated as the attribute is intended for interim use
--  only.  This attribute will be the first candidate for the attribute
--  expiry mechanisms!
--
--    textEncodedORAddress ATTRIBUTE
--        WITH ATTRIBUTE-SYNTAX
--            caseIgnoreStringSyntax
--        (SIZE (1 .. ub-text-encoded-or-address))
--    ::= {pilotAttributeType 2}
--
textEncodedORAddress ATTRIBUTE ::= {
    WITH SYNTAX 				DirectoryString{256}
    EQUALITY MATCHING RULE 		caseIgnoreMatch
	ORDERING MATCHING RULE		caseIgnoreOrderingMatch
	SUBSTRINGS MATCHING RULE 	caseIgnoreSubstringsMatch
	LDAP-SYNTAX 				directoryString.&id
	LDAP-NAME 					{"textEncodedORAddress"}
	LDAP-DESC
		"Text encoding of an X.400 O/R address, as specified in RFC 987."
    ID { pilotAttributeType 2 }
}

-- 9.3.3.  RFC 822 Mailbox
--
--  The RFC822 Mailbox attribute type specifies an electronic mailbox
--  attribute following the syntax specified in RFC 822.  Note that this
--  attribute should not be used for greybook or other non-Internet order
--  mailboxes.
--
--    rfc822Mailbox ATTRIBUTE
--        WITH ATTRIBUTE-SYNTAX
--            caseIgnoreIA5StringSyntax
--            (SIZE (1 .. ub-rfc822-mailbox))
--    ::= {pilotAttributeType 3}
mail ATTRIBUTE ::= {
    WITH SYNTAX 				IA5String (SIZE (0..256))
    EQUALITY MATCHING RULE 		caseIgnoreIA5Match
	SUBSTRINGS MATCHING RULE 	caseIgnoreIA5SubstringsMatch
	LDAP-SYNTAX 				ia5String.&id
	LDAP-NAME 					{"mail", "rfc822Mailbox"}
	LDAP-DESC					"RFC1274: RFC822 Mailbox"
    ID { 0 9 2342 19200300 100 1 3 }
}

-- 9.3.4.  Information
--
--  The Information attribute type specifies any general information
--  pertinent to an object.  It is recommended that specific usage of
--  this attribute type is avoided, and that specific requirements are
--  met by other (possibly additional) attribute types.
--
--    info ATTRIBUTE
--        WITH ATTRIBUTE-SYNTAX
--            caseIgnoreStringSyntax
--            (SIZE (1 .. ub-information))
--    ::= {pilotAttributeType 4}
--
info ATTRIBUTE ::= {
    WITH SYNTAX 				DirectoryString{2048}
    EQUALITY MATCHING RULE 		caseIgnoreMatch
	ORDERING MATCHING RULE		caseIgnoreOrderingMatch
	SUBSTRINGS MATCHING RULE 	caseIgnoreSubstringsMatch
	LDAP-SYNTAX 				directoryString.&id
	LDAP-NAME 					{"info"}
	LDAP-DESC					"RFC1274: general information."
    ID { pilotAttributeType 4 }
}

-- 9.3.5.  Favourite Drink
--
--  The Favourite Drink attribute type specifies the favourite drink of
--  an object (or person).
--
--    favouriteDrink ATTRIBUTE
--        WITH ATTRIBUTE-SYNTAX
--            caseIgnoreStringSyntax
--            (SIZE (1 .. ub-favourite-drink))
--    ::= {pilotAttributeType 5}
--
favouriteDrink ATTRIBUTE ::= {
    WITH SYNTAX 				DirectoryString{256}
    EQUALITY MATCHING RULE 		caseIgnoreMatch
	ORDERING MATCHING RULE		caseIgnoreOrderingMatch
	SUBSTRINGS MATCHING RULE 	caseIgnoreSubstringsMatch
	LDAP-SYNTAX 				directoryString.&id
	LDAP-NAME 					{"favoriteDrink", "favouriteDrink", "drink"}
	LDAP-DESC					"RFC1274: favorite drink."
    ID { pilotAttributeType 5 }
}

-- 9.3.6.  Room Number
--
--  The Room Number attribute type specifies the room number of an
--  object.  Note that the commonName attribute should be used for naming
--  room objects.
--
--    roomNumber ATTRIBUTE
--        WITH ATTRIBUTE-SYNTAX
--            caseIgnoreStringSyntax
--            (SIZE (1 .. ub-room-number))
--    ::= {pilotAttributeType 6}
--
roomNumber ATTRIBUTE ::= {
    WITH SYNTAX 				DirectoryString{256}
    EQUALITY MATCHING RULE 		caseIgnoreMatch
	ORDERING MATCHING RULE		caseIgnoreOrderingMatch
	SUBSTRINGS MATCHING RULE 	caseIgnoreSubstringsMatch
	LDAP-SYNTAX 				directoryString.&id
	LDAP-NAME 					{"roomNumber"}
	LDAP-DESC					"RFC1274: room number."
    ID { pilotAttributeType 6 }
}

-- Note that, in ITU Rec. X.520, fax syntax's directory equivalent is `NULL`.
-- I believe this is either in error, or to prevent the use of a large and
-- complex data type in directory attributes. For this reason, this attribute
-- type will not be implemented as a directory attribute. Also, the LDAP syntax
-- limits this attribute's size to 25000 bytes, which is too small for most
-- photos.
--
-- photo ATTRIBUTE ::= {
--  WITH SYNTAX 				NULL
-- 	LDAP-SYNTAX 				fax.&id
-- 	LDAP-NAME 					{"photo"}
-- 	LDAP-DESC					"RFC1274: photo (G3 fax)."
--     ID { pilotAttributeType 7 }
-- }

userClass ATTRIBUTE ::= {
    WITH SYNTAX 				DirectoryString{256}
    EQUALITY MATCHING RULE 		caseIgnoreMatch
	ORDERING MATCHING RULE		caseIgnoreOrderingMatch
	SUBSTRINGS MATCHING RULE 	caseIgnoreSubstringsMatch
	LDAP-SYNTAX 				directoryString.&id
	LDAP-NAME 					{"userClass"}
	LDAP-DESC					"RFC1274: category of user."
    ID { pilotAttributeType 8 }
}

host ATTRIBUTE ::= {
    WITH SYNTAX 				DirectoryString{256}
    EQUALITY MATCHING RULE 		caseIgnoreMatch
	ORDERING MATCHING RULE		caseIgnoreOrderingMatch
	SUBSTRINGS MATCHING RULE 	caseIgnoreSubstringsMatch
	LDAP-SYNTAX 				directoryString.&id
	LDAP-NAME 					{"host"}
	LDAP-DESC					"RFC1274: host computer."
    ID { pilotAttributeType 9 }
}

manager ATTRIBUTE ::= {
    WITH SYNTAX 				DistinguishedName
    EQUALITY MATCHING RULE 		distinguishedNameMatch
	LDAP-SYNTAX 				dn.&id
	LDAP-NAME 					{"manager"}
	LDAP-DESC					"RFC1274: DN of manager."
    ID { pilotAttributeType 10 }
}

documentIdentifier ATTRIBUTE ::= {
    WITH SYNTAX 				DirectoryString{256}
    EQUALITY MATCHING RULE 		caseIgnoreMatch
	ORDERING MATCHING RULE		caseIgnoreOrderingMatch
	SUBSTRINGS MATCHING RULE 	caseIgnoreSubstringsMatch
	LDAP-SYNTAX 				directoryString.&id
	LDAP-NAME 					{"documentIdentifier"}
	LDAP-DESC					"RFC1274: unique identifier of document."
    ID { pilotAttributeType 11 }
}

documentTitle ATTRIBUTE ::= {
    WITH SYNTAX 				DirectoryString{256}
    EQUALITY MATCHING RULE 		caseIgnoreMatch
	ORDERING MATCHING RULE		caseIgnoreOrderingMatch
	SUBSTRINGS MATCHING RULE 	caseIgnoreSubstringsMatch
	LDAP-SYNTAX 				directoryString.&id
	LDAP-NAME 					{"documentTitle"}
	LDAP-DESC					"RFC1274: title of document."
    ID { pilotAttributeType 12 }
}

documentVersion ATTRIBUTE ::= {
    WITH SYNTAX 				DirectoryString{256}
    EQUALITY MATCHING RULE 		caseIgnoreMatch
	ORDERING MATCHING RULE		caseIgnoreOrderingMatch
	SUBSTRINGS MATCHING RULE 	caseIgnoreSubstringsMatch
	LDAP-SYNTAX 				directoryString.&id
	LDAP-NAME 					{"documentVersion"}
	LDAP-DESC					"RFC1274: version of document."
    ID { pilotAttributeType 13 }
}

documentAuthor ATTRIBUTE ::= {
    WITH SYNTAX 				DistinguishedName
    EQUALITY MATCHING RULE 		distinguishedNameMatch
	LDAP-SYNTAX 				dn.&id
	LDAP-NAME 					{"documentAuthor"}
	LDAP-DESC					"RFC1274: DN of author of document."
    ID { pilotAttributeType 14 }
}

documentLocation ATTRIBUTE ::= {
    WITH SYNTAX 				DirectoryString{256}
    EQUALITY MATCHING RULE 		caseIgnoreMatch
	ORDERING MATCHING RULE		caseIgnoreOrderingMatch
	SUBSTRINGS MATCHING RULE 	caseIgnoreSubstringsMatch
	LDAP-SYNTAX 				directoryString.&id
	LDAP-NAME 					{"documentLocation"}
	LDAP-DESC					"RFC1274: location of document original."
    ID { pilotAttributeType 15 }
}

homeTelephoneNumber ATTRIBUTE ::= {
    WITH SYNTAX 				TelephoneNumber
    EQUALITY MATCHING RULE 		telephoneNumberMatch
	SUBSTRINGS MATCHING RULE 	telephoneNumberSubstringsMatch
	LDAP-SYNTAX 				telephoneNr.&id
	LDAP-NAME 					{"homeTelephoneNumber", "homePhone"}
	LDAP-DESC					"RFC1274: home telephone number"
    ID { pilotAttributeType 20 }
}

secretary ATTRIBUTE ::= {
    WITH SYNTAX 				DistinguishedName
    EQUALITY MATCHING RULE 		distinguishedNameMatch
	LDAP-SYNTAX 				dn.&id
	LDAP-NAME 					{"secretary"}
	LDAP-DESC					"RFC1274: DN of secretary."
    ID { pilotAttributeType 21 }
}

-- The X.500 SYNTAX-NAME is also `NULL` for this attribute.
--
-- 9.3.18.  Other Mailbox
--
--  The Other Mailbox attribute type specifies values for electronic
--  mailbox types other than X.400 and rfc822.
--
--    otherMailbox ATTRIBUTE
--        WITH ATTRIBUTE-SYNTAX
--            SEQUENCE {
--                    mailboxType PrintableString, // e.g. Telemail
--                    mailbox IA5String // e.g. X378:Joe
--            }
--    ::= {pilotAttributeType 22}
--
-- attributetype ( 0.9.2342.19200300.100.1.22 NAME 'otherMailbox'
-- 	SYNTAX 1.3.6.1.4.1.1466.115.121.1.39 )

-- DNS Records have been skipped, because the syntax is completely undocumented
-- and not appropriate for storing generic DNS information.

associatedDomain ATTRIBUTE ::= {
    WITH SYNTAX 				IA5String
    EQUALITY MATCHING RULE 		caseIgnoreIA5Match
	SUBSTRINGS MATCHING RULE 	caseIgnoreIA5SubstringsMatch
	LDAP-SYNTAX 				ia5String.&id
	LDAP-NAME 					{"associatedDomain"}
    ID { pilotAttributeType 37 }
}

associatedName ATTRIBUTE ::= {
    WITH SYNTAX 				DistinguishedName
    EQUALITY MATCHING RULE 		distinguishedNameMatch
	LDAP-SYNTAX 				dn.&id
	LDAP-NAME 					{"associatedName"}
	LDAP-DESC					"RFC1274: DN of entry associated with domain."
    ID { pilotAttributeType 38 }
}

homePostalAddress ATTRIBUTE ::= {
    WITH SYNTAX 				PostalAddress
    EQUALITY MATCHING RULE 		caseIgnoreListMatch
	SUBSTRINGS MATCHING RULE 	caseIgnoreListSubstringsMatch
	LDAP-SYNTAX 				postalAddr.&id
	LDAP-NAME 					{"homePostalAddress"}
	LDAP-DESC					"RFC1274: home postal address"
    ID { pilotAttributeType 39 }
}

personalTitle ATTRIBUTE ::= {
    WITH SYNTAX 				DirectoryString{256}
    EQUALITY MATCHING RULE 		caseIgnoreMatch
	ORDERING MATCHING RULE		caseIgnoreOrderingMatch
	SUBSTRINGS MATCHING RULE 	caseIgnoreSubstringsMatch
	LDAP-SYNTAX 				directoryString.&id
	LDAP-NAME 					{"personalTitle"}
	LDAP-DESC					"RFC1274: personal title."
    ID { pilotAttributeType 40 }
}

mobileTelephoneNumber ATTRIBUTE ::= {
    WITH SYNTAX 				TelephoneNumber
    EQUALITY MATCHING RULE 		telephoneNumberMatch
	SUBSTRINGS MATCHING RULE 	telephoneNumberSubstringsMatch
	LDAP-SYNTAX 				telephoneNr.&id
	LDAP-NAME 					{"mobileTelephoneNumber", "mobile"}
	LDAP-DESC					"RFC1274: mobile telephone number"
    ID { pilotAttributeType 41 }
}

pagerTelephoneNumber ATTRIBUTE ::= {
    WITH SYNTAX 				TelephoneNumber
    EQUALITY MATCHING RULE 		telephoneNumberMatch
	SUBSTRINGS MATCHING RULE 	telephoneNumberSubstringsMatch
	LDAP-SYNTAX 				telephoneNr.&id
	LDAP-NAME 					{"pagerTelephoneNumber", "pager"}
	LDAP-DESC					"RFC1274: pager telephone number"
    ID { pilotAttributeType 42 }
}

friendlyCountryName ATTRIBUTE ::= {
    WITH SYNTAX 				DirectoryString{256}
    EQUALITY MATCHING RULE 		caseIgnoreMatch
	ORDERING MATCHING RULE		caseIgnoreOrderingMatch
	SUBSTRINGS MATCHING RULE 	caseIgnoreSubstringsMatch
	LDAP-SYNTAX 				directoryString.&id
	LDAP-NAME 					{"friendlyCountryName", "co"}
	LDAP-DESC					"RFC1274: friendly country name."
    ID { pilotAttributeType 43 }
}

-- Be advised: there is another uniqueIdentifier defined in X.520.
uniqueIdentifier ATTRIBUTE ::= {
    WITH SYNTAX 				DirectoryString{256}
    EQUALITY MATCHING RULE 		caseIgnoreMatch
	ORDERING MATCHING RULE		caseIgnoreOrderingMatch
	SUBSTRINGS MATCHING RULE 	caseIgnoreSubstringsMatch
	LDAP-SYNTAX 				directoryString.&id
	LDAP-NAME 					{"uniqueIdentifier"}
	LDAP-DESC					"RFC1274: unique identifer."
    ID { pilotAttributeType 44 }
}

organizationalStatus ATTRIBUTE ::= {
    WITH SYNTAX 				DirectoryString{256}
    EQUALITY MATCHING RULE 		caseIgnoreMatch
	ORDERING MATCHING RULE		caseIgnoreOrderingMatch
	SUBSTRINGS MATCHING RULE 	caseIgnoreSubstringsMatch
	LDAP-SYNTAX 				directoryString.&id
	LDAP-NAME 					{"organizationalStatus"}
	LDAP-DESC					"RFC1274: organizational status."
    ID { pilotAttributeType 45 }
}

janetMailbox ATTRIBUTE ::= {
    WITH SYNTAX 				IA5String
    EQUALITY MATCHING RULE 		caseIgnoreIA5Match
	SUBSTRINGS MATCHING RULE 	caseIgnoreIA5SubstringsMatch
	LDAP-SYNTAX 				ia5String.&id
	LDAP-NAME 					{"janetMailbox"}
	LDAP-DESC					"RFC1274: Janet mailbox"
    ID { pilotAttributeType 46 }
}

buildingName ATTRIBUTE ::= {
    WITH SYNTAX 				DirectoryString{256}
    EQUALITY MATCHING RULE 		caseIgnoreMatch
	ORDERING MATCHING RULE		caseIgnoreOrderingMatch
	SUBSTRINGS MATCHING RULE 	caseIgnoreSubstringsMatch
	LDAP-SYNTAX 				directoryString.&id
	LDAP-NAME 					{"buildingName"}
	LDAP-DESC					"RFC1274: name of building."
    ID { pilotAttributeType 48 }
}

-- TODO: All of the QoS attributes below.
-- 9.3.39.  DSA Quality
--
--  The DSA Quality attribute type specifies the purported quality of a
--  DSA.  It allows a DSA manager to indicate the expected level of
--  availability of the DSA. See [8] for details of the syntax.
--
--    dSAQuality ATTRIBUTE
--            WITH ATTRIBUTE-SYNTAX DSAQualitySyntax
--            SINGLE VALUE
--    ::= {pilotAttributeType 49}
--
-- attributetype ( 0.9.2342.19200300.100.1.49 NAME 'dSAQuality'
-- 	DESC 'RFC1274: DSA Quality'
-- 	SYNTAX 1.3.6.1.4.1.1466.115.121.1.19 SINGLE-VALUE )

-- 9.3.40.  Single Level Quality
--
--  The Single Level Quality attribute type specifies the purported data
--  quality at the level immediately below in the DIT.  See [8] for
--  details of the syntax.
--
--    singleLevelQuality ATTRIBUTE
--            WITH ATTRIBUTE-SYNTAX DataQualitySyntax
--            SINGLE VALUE
--    ::= {pilotAttributeType 50}
--
-- attributetype ( 0.9.2342.19200300.100.1.50 NAME 'singleLevelQuality'
-- 	DESC 'RFC1274: Single Level Quality'
-- 	SYNTAX 1.3.6.1.4.1.1466.115.121.1.13 SINGLE-VALUE )

-- 9.3.41.  Subtree Minimum Quality
--
--  The Subtree Minimum Quality attribute type specifies the purported
--  minimum data quality for a DIT subtree.  See [8] for more discussion
--  and details of the syntax.
--
--    subtreeMinimumQuality ATTRIBUTE
--            WITH ATTRIBUTE-SYNTAX DataQualitySyntax
--            SINGLE VALUE Defaults to singleLevelQuality
--    ::= {pilotAttributeType 51}
--
-- attributetype ( 0.9.2342.19200300.100.1.51 NAME 'subtreeMinimumQuality'
-- 	DESC 'RFC1274: Subtree Minimum Quality'
-- 	SYNTAX 1.3.6.1.4.1.1466.115.121.1.13 SINGLE-VALUE )

-- 9.3.42.  Subtree Maximum Quality
--
--  The Subtree Maximum Quality attribute type specifies the purported
--  maximum data quality for a DIT subtree.  See [8] for more discussion
--  and details of the syntax.
--
--    subtreeMaximumQuality ATTRIBUTE
--            WITH ATTRIBUTE-SYNTAX DataQualitySyntax
--            SINGLE VALUE
--    ::= {pilotAttributeType 52}
--
-- attributetype ( 0.9.2342.19200300.100.1.52 NAME 'subtreeMaximumQuality'
-- 	DESC 'RFC1274: Subtree Maximum Quality'
-- 	SYNTAX 1.3.6.1.4.1.1466.115.121.1.13 SINGLE-VALUE )

-- 9.3.43.  Personal Signature
--
--  The Personal Signature attribute type allows for a representation of
--  a person's signature.  This should be encoded in G3 fax as explained
--  in recommendation T.4, with an ASN.1 wrapper to make it compatible
--  with an X.400 BodyPart as defined in X.420.
--
--    IMPORT  G3FacsimileBodyPart  FROM  {   mhs-motis   ipms   modules
--    information-objects }
--
--    personalSignature ATTRIBUTE
--        WITH ATTRIBUTE-SYNTAX
--            CHOICE {
--                g3-facsimile [3] G3FacsimileBodyPart
--                }
--        (SIZE (1 .. ub-personal-signature))
--    ::= {pilotAttributeType 53}
--
-- attributetype ( 0.9.2342.19200300.100.1.53 NAME 'personalSignature'
-- 	DESC 'RFC1274: Personal Signature (G3 fax)'
-- 	SYNTAX 1.3.6.1.4.1.1466.115.121.1.23 )

-- 9.3.44.  DIT Redirect
--
--  The DIT Redirect attribute type is used to indicate that the object
--  described by one entry now has a newer entry in the DIT.  The entry
--  containing the redirection attribute should be expired after a
--  suitable grace period.  This attribute may be used when an individual
--  changes his/her place of work, and thus acquires a new organisational
--  DN.
--
--    dITRedirect ATTRIBUTE
--        WITH ATTRIBUTE-SYNTAX
--            distinguishedNameSyntax
--    ::= {pilotAttributeType 54}
--
dITRedirect ATTRIBUTE ::= {
    WITH SYNTAX 				DistinguishedName
    EQUALITY MATCHING RULE 		distinguishedNameMatch
	LDAP-SYNTAX 				dn.&id
	LDAP-NAME 					{"dITRedirect"}
	LDAP-DESC					"RFC1274: DIT Redirect."
    ID { pilotAttributeType 54 }
}

audio ATTRIBUTE ::= {
    WITH SYNTAX 				OCTET STRING (1..ub-audio)
	LDAP-SYNTAX 				octetString.&id
	LDAP-NAME 					{"audio"}
	LDAP-DESC					"RFC1274: audio (u-law)."
    ID { pilotAttributeType 55 }
}

aRecord ATTRIBUTE ::= {
    WITH SYNTAX             IA5String
    LDAP-SYNTAX             ia5String.&id
    LDAP-NAME               {"aRecord"}
    ID                      { 0 9 2342 19200300 100 1 26 }
}

mDRecord ATTRIBUTE ::= {
    WITH SYNTAX             IA5String
    LDAP-SYNTAX             ia5String.&id
    LDAP-NAME               {"mDRecord"}
    ID                      { 0 9 2342 19200300 100 1 27 }
}

mxRecord ATTRIBUTE ::= {
    WITH SYNTAX             IA5String
    LDAP-SYNTAX             ia5String.&id
    LDAP-NAME               {"mxRecord"}
    ID                      { 0 9 2342 19200300 100 1 28 }
}

nSRecord ATTRIBUTE ::= {
    WITH SYNTAX             IA5String
    LDAP-SYNTAX             ia5String.&id
    LDAP-NAME               {"nSRecord"}
    ID                      { 0 9 2342 19200300 100 1 29 }
}

sOARecord ATTRIBUTE ::= {
    WITH SYNTAX             IA5String
    LDAP-SYNTAX             ia5String.&id
    LDAP-NAME               {"sOARecord"}
    ID                      { 0 9 2342 19200300 100 1 30 }
}

cNAMERecord ATTRIBUTE ::= {
    WITH SYNTAX             IA5String
    LDAP-SYNTAX             ia5String.&id
    LDAP-NAME               {"cNAMERecord"}
    ID                      { 0 9 2342 19200300 100 1 31 }
}

-- 9.3.46.  Publisher of Document
--
--  The Publisher of Document attribute is the person and/or organization
--  that published a document.
--
--    documentPublisher ATTRIBUTE
--            WITH ATTRIBUTE SYNTAX caseIgnoreStringSyntax
--    ::= {pilotAttributeType 56}
--
documentPublisher ATTRIBUTE ::= {
    WITH SYNTAX 				DirectoryString{256}
    EQUALITY MATCHING RULE 		caseIgnoreMatch
	ORDERING MATCHING RULE		caseIgnoreOrderingMatch
	SUBSTRINGS MATCHING RULE 	caseIgnoreSubstringsMatch
	LDAP-SYNTAX 				directoryString.&id
	LDAP-NAME 					{"documentPublisher"}
	LDAP-DESC					"RFC1274: publisher of document."
    ID { pilotAttributeType 56 }
}

MailPreferenceOptionSyntax ::= ENUMERATED {
    no-list-inclusion(0),

    -- may be added to any lists
    any-list-inclusion(1),

    -- may be added to lists
    -- which the list provider
    -- views as related to the
    -- users professional inter-
    -- ests, perhaps evaluated
    -- from the business of the
    -- organisation or keywords
    -- in the entry.
    professional-list-inclusion(2)
}

mailPreferenceOption ATTRIBUTE ::= {
	WITH SYNTAX                 MailPreferenceOptionSyntax
    EQUALITY MATCHING RULE      integerMatch
    SINGLE VALUE                TRUE
    LDAP-SYNTAX                 integer.&id
	LDAP-NAME                   { "mailPreferenceOption" }
	ID                          { pilotAttributeType 47 }
}

ub-document-identifier INTEGER ::= 256
ub-document-location INTEGER ::= 256
ub-document-title INTEGER ::= 256
ub-document-version INTEGER ::= 256
ub-favourite-drink INTEGER ::= 256
ub-host INTEGER ::= 256
ub-information INTEGER ::= 2048
ub-unique-identifier INTEGER ::= 256
ub-personal-title INTEGER ::= 256
ub-photo INTEGER ::= 250000
ub-rfc822-mailbox INTEGER ::= 256
ub-room-number INTEGER ::= 256
ub-text-or-address INTEGER ::= 256
ub-user-class INTEGER ::= 256
ub-user-identifier INTEGER ::= 256
ub-organizational-status INTEGER ::= 256
ub-janet-mailbox INTEGER ::= 256
ub-building-name INTEGER ::= 256
ub-personal-signature INTEGER ::= 50000
ub-audio INTEGER ::= 250000

-- TODO: Should lastModifiedTime and lastModifiedBy be kept?
pilotObject OBJECT-CLASS ::= {
	SUBCLASS OF {top}
	MAY CONTAIN {
		info
		-- | photo
		| manager
		| uniqueIdentifier
		-- | lastModifiedTime
		-- | lastModifiedBy
		| dITRedirect
		| audio
	}
	LDAP-NAME {"pilotObject"}
	LDAP-DESC "RFC1274: pilot object"
	ID { pilotObjectClass 3 }
}

-- 8.3.2.  Pilot Person
--
--  The PilotPerson object class is used as a sub-class of person, to
--  allow the use of a number of additional attributes to be assigned to
--  entries of object class person.
--
--    pilotPerson OBJECT-CLASS
--        SUBCLASS OF person
--        MAY CONTAIN {
--                    userid,
--                    textEncodedORAddress,
--                    rfc822Mailbox,
--                    favouriteDrink,
--                    roomNumber,
--                    userClass,
--                    homeTelephoneNumber,
--                    homePostalAddress,
--                    secretary,
--                    personalTitle,
--                    preferredDeliveryMethod,
--                    businessCategory,
--                    janetMailbox,
--                    otherMailbox,
--                    mobileTelephoneNumber,
--                    pagerTelephoneNumber,
--                    organizationalStatus,
--                    mailPreferenceOption,
--                    personalSignature}
--    ::= {pilotObjectClass 4}
--
pilotPerson OBJECT-CLASS ::= {
	SUBCLASS OF {person}
	KIND structural
	MAY CONTAIN {
		uid
		| textEncodedORAddress
		| rfc822Mailbox
		| favouriteDrink
		| roomNumber
		| userClass
		| homeTelephoneNumber
		| homePostalAddress
		| secretary
		| personalTitle
		| preferredDeliveryMethod
		| businessCategory
		| janetMailbox
		-- | otherMailbox
		| mobileTelephoneNumber
		| pagerTelephoneNumber
		| organizationalStatus
		| mailPreferenceOption
		-- | personalSignature
	}
	LDAP-NAME {"pilotPerson", "newPilotPerson"}
	ID { pilotObjectClass 4 }
}

-- 8.3.3.  Account
--
--  The Account object class is used to define entries representing
--  computer accounts.  The userid attribute should be used for naming
--  entries of this object class.
--
--    account OBJECT-CLASS
--        SUBCLASS OF top
--        MUST CONTAIN {
--            userid}
--        MAY CONTAIN {
--            description,
--            seeAlso,
--            localityName,
--            organizationName,
--            organizationalUnitName,
--            host}
--    ::= {pilotObjectClass 5}
--
account OBJECT-CLASS ::= {
	SUBCLASS OF {top}
	KIND structural
	MUST CONTAIN {uid}
	MAY CONTAIN {
		description
		| seeAlso
		| localityName
		| organizationName
		| organizationalUnitName
		| host
	}
	LDAP-NAME {"account"}
	ID { pilotObjectClass 5 }
}

-- 8.3.4.  Document
--
--  The Document object class is used to define entries which represent
--  documents.
--
--    document OBJECT-CLASS
--        SUBCLASS OF top
--        MUST CONTAIN {
--            documentIdentifier}
--        MAY CONTAIN {
--            commonName,
--            description,
--            seeAlso,
--            localityName,
--            organizationName,
--            organizationalUnitName,
--            documentTitle,
--            documentVersion,
--            documentAuthor,
--            documentLocation,
--            documentPublisher}
--    ::= {pilotObjectClass 6}
--
document OBJECT-CLASS ::= {
	SUBCLASS OF {top}
	KIND structural
	MUST CONTAIN {
		documentIdentifier
	}
	MAY CONTAIN {
		commonName
		| description
		| seeAlso
		| localityName
		| organizationName
		| organizationalUnitName
		| documentTitle
		| documentVersion
		| documentAuthor
		| documentLocation
		| documentPublisher
	}
	LDAP-NAME {"document"}
	ID { pilotObjectClass 6 }
}

-- 8.3.5.  Room
--
--  The Room object class is used to define entries representing rooms.
--  The commonName attribute should be used for naming pentries of this
--  object class.
--
--    room OBJECT-CLASS
--        SUBCLASS OF top
--        MUST CONTAIN {
--            commonName}
--        MAY CONTAIN {
--            roomNumber,
--            description,
--            seeAlso,
--            telephoneNumber}
--    ::= {pilotObjectClass 7}
--
room OBJECT-CLASS ::= {
	SUBCLASS OF {top}
	KIND structural
	MUST CONTAIN {
		commonName
	}
	MAY CONTAIN {
		roomNumber
		| description
		| seeAlso
		| telephoneNumber
	}
	LDAP-NAME {"room"}
	ID { pilotObjectClass 7 }
}

-- 8.3.6.  Document Series
--
--  The Document Series object class is used to define an entry which
--  represents a series of documents (e.g., The Request For Comments
--  papers).
--
--    documentSeries OBJECT-CLASS
--        SUBCLASS OF top
--        MUST CONTAIN {
--            commonName}
--        MAY CONTAIN {
--            description,
--            seeAlso,
--            telephoneNumber,
--            localityName,
--            organizationName,
--            organizationalUnitName}
--    ::= {pilotObjectClass 9}
--
documentSeries OBJECT-CLASS ::= {
	SUBCLASS OF {top}
	KIND structural
	MUST CONTAIN {
		commonName
	}
	MAY CONTAIN {
		description
		| seeAlso
		| telephoneNumber
		| localityName
		| organizationName
		| organizationalUnitName
	}
	LDAP-NAME {"documentSeries"}
	ID { pilotObjectClass 9 }
}

-- 8.3.7.  Domain
--
--  The Domain object class is used to define entries which represent DNS
--  or NRS domains.  The domainComponent attribute should be used for
--  naming entries of this object class.  The usage of this object class
--  is described in more detail in [3].
--
--    domain OBJECT-CLASS
--        SUBCLASS OF top
--        MUST CONTAIN {
--            domainComponent}
--        MAY CONTAIN {
--            associatedName,
--            organizationName,
--            organizationalAttributeSet}
--    ::= {pilotObjectClass 13}
--
domain OBJECT-CLASS ::= {
	SUBCLASS OF {top}
	KIND structural
	MUST CONTAIN {
		dc
	}
	MAY CONTAIN {
		associatedName
		| organizationName
		| description
		| businessCategory
		| seeAlso
		| searchGuide
		| userPassword
		| localityName
		| stateOrProvinceName
		| physicalDeliveryOfficeName
		| postalAddress
		| postalCode
		| postOfficeBox
		| streetAddress
		| facsimileTelephoneNumber
		| internationalISDNNumber
		| telephoneNumber
		-- | teletexTerminalIdentifier
		| telexNumber
		| preferredDeliveryMethod
		| destinationIndicator
		| registeredAddress
		| x121Address
	}
	LDAP-NAME {"domain"}
	ID { pilotObjectClass 13 }
}

-- 8.3.8.  RFC822 Local Part
--
--  The RFC822 Local Part object class is used to define entries which
--  represent the local part of RFC822 mail addresses.  This treats this
--  part of an RFC822 address as a domain.  The usage of this object
--  class is described in more detail in [3].
--
--    rFC822localPart OBJECT-CLASS
--        SUBCLASS OF domain
--        MAY CONTAIN {
--            commonName,
--            surname,
--            description,
--            seeAlso,
--            telephoneNumber,
--            postalAttributeSet,
--            telecommunicationAttributeSet}
--    ::= {pilotObjectClass 14}
--
rFC822localPart OBJECT-CLASS ::= {
	SUBCLASS OF {domain}
	KIND structural
	MAY CONTAIN {
		commonName
		| description
		| destinationIndicator
		| facsimileTelephoneNumber
		| internationalISDNNumber
		| physicalDeliveryOfficeName
		| postalAddress
		| postalCode
		| postOfficeBox
		| preferredDeliveryMethod
		| registeredAddress
		| seeAlso
		| streetAddress
		| surname
		| telephoneNumber
		-- | teletexTerminalIdentifier
		| telexNumber
		| x121Address
	}
	LDAP-NAME {"rFC822localPart"}
	ID { pilotObjectClass 14 }
}

-- 8.3.9.  DNS Domain
--
--  The DNS Domain (Domain NameServer) object class is used to define
--  entries for DNS domains.  The usage of this object class is described
--  in more detail in [3].
--
--    dNSDomain OBJECT-CLASS
--        SUBCLASS OF domain
--        MAY CONTAIN {
--            ARecord,
--            MDRecord,
--            MXRecord,
--            NSRecord,
--            SOARecord,
--            CNAMERecord}
--    ::= {pilotObjectClass 15}
--
-- objectclass ( 0.9.2342.19200300.100.4.15 NAME 'dNSDomain'
-- 	SUP domain STRUCTURAL
-- 	MAY ( ARecord $ MDRecord $ MXRecord $ NSRecord $
-- 		SOARecord $ CNAMERecord )
-- 	)

dNSDomain OBJECT-CLASS ::= {
    SUBCLASS OF         { domain }
	KIND                structural
    MAY CONTAIN         {
        aRecord
        | mDRecord
        | mxRecord
        | nSRecord
        | sOARecord
        | cNAMERecord
    }
	LDAP-NAME           { "dNSDomain" }
	ID                  { 0 9 2342 19200300 100 4 15 }
}

-- 8.3.10.  Domain Related Object
--
--  The Domain Related Object object class is used to define entries
--  which represent DNS/NRS domains which are "equivalent" to an X.500
--  domain: e.g., an organisation or organisational unit.  The usage of
--  this object class is described in more detail in [3].
--
--    domainRelatedObject OBJECT-CLASS
--        SUBCLASS OF top
--        MUST CONTAIN {
--            associatedDomain}
--    ::= {pilotObjectClass 17}
--
domainRelatedObject OBJECT-CLASS ::= {
	SUBCLASS OF {top}
	KIND auxiliary
	MUST CONTAIN {
		associatedDomain
	}
	LDAP-NAME {"domainRelatedObject"}
	LDAP-DESC "RFC1274: an object related to an domain."
	ID { pilotObjectClass 17 }
}

-- 8.3.11.  Friendly Country
--
--  The Friendly Country object class is used to define country entries
--  in the DIT.  The object class is used to allow friendlier naming of
--  countries than that allowed by the object class country.  The naming
--  attribute of object class country, countryName, has to be a 2 letter
--  string defined in ISO 3166.
--
--    friendlyCountry OBJECT-CLASS
--        SUBCLASS OF country
--        MUST CONTAIN {
--            friendlyCountryName}
--    ::= {pilotObjectClass 18}
--
friendlyCountry OBJECT-CLASS ::= {
	SUBCLASS OF {country}
	KIND structural
	MUST CONTAIN {
		friendlyCountryName
	}
	LDAP-NAME {"friendlyCountry"}
	ID { pilotObjectClass 18 }
}

-- 8.3.12.  Simple Security Object
--
--  The Simple Security Object object class is used to allow an entry to
--  have a userPassword attribute when an entry's principal object
--  classes do not allow userPassword as an attribute type.
--
--    simpleSecurityObject OBJECT-CLASS
--        SUBCLASS OF top
--        MUST CONTAIN {
--            userPassword }
--    ::= {pilotObjectClass 19}
--
--# (in core.schema)
--# objectclass ( 0.9.2342.19200300.100.4.19 NAME 'simpleSecurityObject'
--#	SUP top AUXILIARY
--#	MUST userPassword )

-- 8.3.13.  Pilot Organization
--
--  The PilotOrganization object class is used as a sub-class of
--  organization and organizationalUnit to allow a number of additional
--  attributes to be assigned to entries of object classes organization
--  and organizationalUnit.
--
--    pilotOrganization OBJECT-CLASS
--        SUBCLASS OF organization, organizationalUnit
--        MAY CONTAIN {
--                    buildingName}
--    ::= {pilotObjectClass 20}
--
pilotOrganization OBJECT-CLASS ::= {
	SUBCLASS OF {organization | organizationalUnit}
	KIND structural
	MAY CONTAIN {
		buildingName
	}
	LDAP-NAME {"pilotOrganization"}
	ID { pilotObjectClass 20 }
}

-- Name Forms

pilotOrganizationNameForm NAME-FORM ::= {
	NAMES				pilotOrganization
	WITH ATTRIBUTES		{organizationName}
	LDAP-NAME			{"pilotOrganizationNameForm"}
	ID					{ id-nf 48 }
}

dNSDomainNameForm NAME-FORM ::= {
	NAMES				dNSDomain
	WITH ATTRIBUTES		{dc}
	LDAP-NAME			{"dNSDomainNameForm"}
	ID					{ id-nf 49 }
}

pilotPersonNameForm NAME-FORM ::= {
	NAMES				pilotPerson
	WITH ATTRIBUTES		{commonName}
	LDAP-NAME			{"pilotPersonNameForm"}
	ID					{ id-nf 52 }
}

accountNameForm NAME-FORM ::= {
	NAMES				account
	WITH ATTRIBUTES		{uid}
	LDAP-NAME			{"accountNameForm"}
	ID					{ id-nf 53 }
}

documentNameForm NAME-FORM ::= {
	NAMES				document
	WITH ATTRIBUTES		{documentIdentifier}
	LDAP-NAME			{"documentNameForm"}
	ID					{ id-nf 54 }
}

roomNameForm NAME-FORM ::= {
	NAMES				room
	WITH ATTRIBUTES		{commonName}
	LDAP-NAME			{"roomNameForm"}
	ID					{ id-nf 55 }
}

documentSeriesNameForm NAME-FORM ::= {
	NAMES				documentSeries
	WITH ATTRIBUTES		{commonName}
	LDAP-NAME			{"documentSeriesNameForm"}
	ID					{ id-nf 56 }
}

domainNameForm NAME-FORM ::= {
	NAMES				domain
	WITH ATTRIBUTES		{dc}
	LDAP-NAME			{"domainNameForm"}
	ID					{ id-nf 57 }
}

friendlyCountryNameForm NAME-FORM ::= {
	NAMES				friendlyCountry
	WITH ATTRIBUTES		{countryName}
	LDAP-NAME			{"friendlyCountryNameForm"}
	ID					{ id-nf 58 }
}

-- TODO: pilotObjectNameForm

END
