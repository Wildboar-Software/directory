PureFTPdSchema {
    iso(1) identified-organization(3) dod(6) internet(1) private(4)
    enterprise(1) wildboar(56490) module(1) pure-ftpd-schema(54)
}
DEFINITIONS
EXPLICIT TAGS
EXTENSIBILITY IMPLIED
::=
BEGIN

EXPORTS ALL;

IMPORTS

    ATTRIBUTE, OBJECT-CLASS, objectIdentifierMatch,
    DistinguishedName, distinguishedNameMatch
        FROM InformationFramework
        {joint-iso-itu-t ds(5) module(1) informationFramework(1) 9}
        WITH SUCCESSORS

	name, UnboundedDirectoryString, distinguishedName, description,

    -- Syntaxes
    printableString, boolean, integer, dn, directoryString, ia5String,
    octetString,

    -- Matching Rules
    caseExactMatch, caseExactOrderingMatch, caseExactSubstringsMatch,
    caseIgnoreMatch, caseIgnoreOrderingMatch, caseIgnoreSubstringsMatch,
    booleanMatch, integerMatch, integerOrderingMatch,
    octetStringMatch, octetStringOrderingMatch, octetStringSubstringsMatch,
    caseIgnoreIA5Match, caseIgnoreIA5SubstringsMatch
		FROM SelectedAttributeTypes
		{joint-iso-itu-t ds(5) module(1) selectedAttributeTypes(5) 9}
		WITH SUCCESSORS

    ;

id-at       OBJECT IDENTIFIER ::= { 1 3 6 1 4 1 6981 11 3 }


ftpQuotaFiles ATTRIBUTE ::= {
    WITH SYNTAX 				INTEGER (0..MAX)
    EQUALITY MATCHING RULE 		integerMatch
    ORDERING MATCHING RULE      integerOrderingMatch
    SINGLE VALUE                TRUE
	LDAP-SYNTAX 				integer.&id
	LDAP-NAME 					{"ftpQuotaFiles"}
    LDAP-DESC                   "Quota (in number of files) for an FTP user."
    ID                          { id-at 1 }
}

ftpQuotaMBytes ATTRIBUTE ::= {
    WITH SYNTAX 				INTEGER (0..MAX)
    EQUALITY MATCHING RULE 		integerMatch
    ORDERING MATCHING RULE      integerOrderingMatch
    SINGLE VALUE                TRUE
	LDAP-SYNTAX 				integer.&id
	LDAP-NAME 					{"ftpQuotaMBytes"}
    LDAP-DESC                   "Quota (in megabytes) for an FTP user"
    ID                          { id-at 2 }
}

ftpUploadRatio ATTRIBUTE ::= {
    WITH SYNTAX 				INTEGER (0..MAX)
    EQUALITY MATCHING RULE 		integerMatch
    ORDERING MATCHING RULE      integerOrderingMatch
    SINGLE VALUE                TRUE
	LDAP-SYNTAX 				integer.&id
	LDAP-NAME 					{"ftpUploadRatio"}
    LDAP-DESC                   "Ratio (compared with FTPRatioDown) for uploaded files"
    ID                          { id-at 3 }
}

ftpDownloadRatio ATTRIBUTE ::= {
    WITH SYNTAX 				INTEGER (0..MAX)
    EQUALITY MATCHING RULE 		integerMatch
    ORDERING MATCHING RULE      integerOrderingMatch
    SINGLE VALUE                TRUE
	LDAP-SYNTAX 				integer.&id
	LDAP-NAME 					{"ftpDownloadRatio"}
    LDAP-DESC                   "Ratio (compared with FTPRatioUp) for downloaded files"
    ID                          { id-at 4 }
}

ftpUploadBandwidth ATTRIBUTE ::= {
    WITH SYNTAX 				INTEGER (0..MAX)
    EQUALITY MATCHING RULE 		integerMatch
    ORDERING MATCHING RULE      integerOrderingMatch
    SINGLE VALUE                TRUE
	LDAP-SYNTAX 				integer.&id
	LDAP-NAME 					{"ftpUploadBandwidth"}
    LDAP-DESC                   "Bandwidth (in KB/s) to limit upload speeds to"
    ID                          { id-at 5 }
}

ftpDownloadBandwidth ATTRIBUTE ::= {
    WITH SYNTAX 				INTEGER (0..MAX)
    EQUALITY MATCHING RULE 		integerMatch
    ORDERING MATCHING RULE      integerOrderingMatch
    SINGLE VALUE                TRUE
	LDAP-SYNTAX 				integer.&id
	LDAP-NAME 					{"ftpDownloadBandwidth"}
    LDAP-DESC                   "Bandwidth (in KB/s) to limit download speeds to"
    ID                          { id-at 6 }
}

ftpStatus ATTRIBUTE ::= {
    WITH SYNTAX 				BOOLEAN
    EQUALITY MATCHING RULE 		booleanMatch
    SINGLE VALUE                TRUE
	LDAP-SYNTAX 				boolean.&id
	LDAP-NAME 					{"ftpStatus"}
    LDAP-DESC                   "Account status: enabled or disabled"
    ID                          { id-at 7 }
}

ftpUid ATTRIBUTE ::= {
    WITH SYNTAX 				INTEGER (0..MAX)
    EQUALITY MATCHING RULE 		integerMatch
    ORDERING MATCHING RULE      integerOrderingMatch
    SINGLE VALUE                TRUE
	LDAP-SYNTAX 				integer.&id
	LDAP-NAME 					{"ftpUid"}
    LDAP-DESC                   "System uid (overrides uidNumber if present)"
    ID                          { id-at 8 }
}

ftpGid ATTRIBUTE ::= {
    WITH SYNTAX 				INTEGER (0..MAX)
    EQUALITY MATCHING RULE 		integerMatch
    ORDERING MATCHING RULE      integerOrderingMatch
    SINGLE VALUE                TRUE
	LDAP-SYNTAX 				integer.&id
	LDAP-NAME 					{"ftpGid"}
    LDAP-DESC                   "System uid (overrides gidNumber if present)"
    ID                          { id-at 9 }
}

pureFTPdUser OBJECT-CLASS ::= {
    SUBCLASS OF     {top}
    KIND            structural
    MAY CONTAIN     {
        ftpStatus
        | ftpQuotaFiles
        | ftpQuotaMBytes
        | ftpUploadRatio
        | ftpDownloadRatio
        | ftpUploadBandwidth
        | ftpDownloadBandwidth
        | ftpUid
        | ftpGid
    }
	LDAP-NAME       {"pureFTPdUser"}
    LDAP-DESC       "PureFTPd user with optional quota, throttling and ratio"
	ID              { 1 3 6 1 4 1 6981 11 2 3 }
}

END
