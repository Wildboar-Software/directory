-- This file contains schema definitions from RFC 2926, which defines a
-- mechanism for mapping between Service Location Protocol (SLP) advertisements
-- and LDAP.
RFC2926ServiceLocationProtocolSchema {
    iso(1) identified-organization(3) dod(6) internet(1) private(4)
        enterprise(1) wildboar(56490) module(1) rfc2926-slp-schema(64)
}
DEFINITIONS
EXPLICIT TAGS
EXTENSIBILITY IMPLIED
::=
BEGIN

EXPORTS ALL;

IMPORTS

    ATTRIBUTE, OBJECT-CLASS, objectIdentifierMatch,
    DistinguishedName, distinguishedNameMatch
        FROM InformationFramework
        {joint-iso-itu-t ds(5) module(1) informationFramework(1) 9 }
        WITH SUCCESSORS

    name, UnboundedDirectoryString, distinguishedName, description,

    -- Syntaxes
    printableString, boolean, integer, dn, directoryString, ia5String,
    octetString,

    -- Matching Rules
    caseExactMatch, caseExactOrderingMatch, caseExactSubstringsMatch,
    caseIgnoreMatch, caseIgnoreOrderingMatch, caseIgnoreSubstringsMatch,
    booleanMatch, integerMatch, integerOrderingMatch,
    octetStringMatch, octetStringOrderingMatch, octetStringSubstringsMatch,
    caseIgnoreIA5Match, caseIgnoreIA5SubstringsMatch
        FROM SelectedAttributeTypes
        {joint-iso-itu-t ds(5) module(1) selectedAttributeTypes(5) 9 }
        WITH SUCCESSORS

    ;

id-james-kempf      OBJECT IDENTIFIER ::= { 1 3 6 1 4 1 6252 }

template-major-version-number ATTRIBUTE ::= {
    WITH SYNTAX                 INTEGER (0..MAX)
    EQUALITY MATCHING RULE      integerMatch
    ORDERING MATCHING RULE      integerOrderingMatch
    SINGLE VALUE                TRUE
    LDAP-SYNTAX                 integer.&id
    LDAP-NAME                   { "template-major-version-number" }
    LDAP-DESC                   "The major version number of the service type template"
    ID { id-james-kempf 2 27 6 1 1 }
}

template-minor-version-number ATTRIBUTE ::= {
    WITH SYNTAX                 INTEGER (0..MAX)
    EQUALITY MATCHING RULE      integerMatch
    ORDERING MATCHING RULE      integerOrderingMatch
    SINGLE VALUE                TRUE
    LDAP-SYNTAX                 integer.&id
    LDAP-NAME                   { "template-minor-version-number" }
    LDAP-DESC                   "The minor version number of the service type template"
    ID { id-james-kempf 2 27 6 1 2 }
}

template-url-syntax ATTRIBUTE ::= {
    WITH SYNTAX                 IA5String
    EQUALITY MATCHING RULE      caseExactIA5Match
    SINGLE VALUE                TRUE
    LDAP-SYNTAX                 ia5String.&id
    LDAP-NAME                   { "template-url-syntax" }
    LDAP-DESC                   "An ABNF grammar describing the service type specific part of the service URL"
    ID { id-james-kempf 2 27 6 1 3 }
}

service-advert-service-type ATTRIBUTE ::= {
    WITH SYNTAX                 IA5String
    EQUALITY MATCHING RULE      caseExactIA5Match
    SINGLE VALUE                TRUE
    LDAP-SYNTAX                 ia5String.&id
    LDAP-NAME                   { "service-advert-service-type" }
    LDAP-DESC                   "The service type of the service advertisement, including the 'service:' prefix."
    ID { id-james-kempf 2 27 6 1 4 }
}

service-advert-scopes ATTRIBUTE ::= {
    WITH SYNTAX                 IA5String
    EQUALITY MATCHING RULE      caseExactIA5Match
    LDAP-SYNTAX                 ia5String.&id
    LDAP-NAME                   { "service-advert-scopes" }
    LDAP-DESC                   "A list of scopes for a service advertisement."
    ID { id-james-kempf 2 27 6 1 5 }
}

service-advert-url-authenticator ATTRIBUTE ::= {
    WITH SYNTAX                     IA5String
    SINGLE VALUE                    TRUE
    LDAP-SYNTAX                     ia5String.&id
    LDAP-NAME                       { "service-advert-url-authenticator" }
    LDAP-DESC                       "The authenticator for the URL, null if none."
    ID { id-james-kempf 2 27 6 1 6 }
}

service-advert-attribute-authenticator ATTRIBUTE ::= {
    WITH SYNTAX                     IA5String
    SINGLE VALUE                    TRUE
    LDAP-SYNTAX                     ia5String.&id
    LDAP-NAME                       { "service-advert-attribute-authenticator" }
    LDAP-DESC                       "The authenticator for the attribute list, null if none."
    ID { id-james-kempf 2 27 6 1 7 }
}

slpService OBJECT-CLASS ::= {
    SUBCLASS OF { top }
    KIND                abstract
    MUST CONTAIN {
        template-major-version-number
        | template-minor-version-number
        | description
        | template-url-syntax
        | service-advert-service-type
        | service-advert-scopes
    }
    MAY CONTAIN {
        service-advert-url-authenticator
        | service-advert-attribute-authenticator
    }
    LDAP-NAME { "slpService" }
    LDAP-DESC           "authentication password mix in class"
    ID { id-james-kempf 2 27 6 2 1 }
}

END
