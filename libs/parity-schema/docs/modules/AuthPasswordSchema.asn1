-- This file contains schema definitions from RFC 3112, which defines the
-- authentication password schema.
AuthPasswordSchema {
    iso(1) identified-organization(3) dod(6) internet(1) private(4)
    enterprise(1) wildboar(56490) module(1) auth-password-schema(62)
}
DEFINITIONS
EXPLICIT TAGS
EXTENSIBILITY IMPLIED
::=
BEGIN

EXPORTS ALL;

IMPORTS

    ATTRIBUTE, OBJECT-CLASS, SYNTAX-NAME, MATCHING-RULE
        FROM InformationFramework
        {joint-iso-itu-t ds(5) module(1) informationFramework(1) 9}
        WITH SUCCESSORS

    -- Syntaxes
    ia5String, octetString, caseExactIA5Match
		FROM SelectedAttributeTypes
		{joint-iso-itu-t ds(5) module(1) selectedAttributeTypes(5) 9}
		WITH SUCCESSORS

    AlgorithmIdentifier{}, SupportedAlgorithms
        FROM AuthenticationFramework
        {joint-iso-itu-t ds(5) module(1) authenticationFramework(7) 9}
        WITH SUCCESSORS

    ;

id-at-openldap-schema       OBJECT IDENTIFIER ::= { 1 3 6 1 4 1 4203 1 }

PlaintextPasswordSyntax ::= OCTET STRING

-- You might wonder: why can't you use `HASH` defined in `AuthenticationFramework`?
-- It cannot be used because it specifies that the hash is taken over the
-- DER-encoded element, rather than just the value octets.
-- IETF RFC 3112 Auth Passwords only hash the password itself as an `OCTET STRING`.
AuthPasswordSyntax ::= SEQUENCE {
    algorithmIdentifier  AlgorithmIdentifier{{SupportedAlgorithms}},
    hashValue            PlaintextPasswordSyntax,
    ...
}

-- ( 1.3.6.1.4.1.4203.1.1.2
-- DESC 'authentication password syntax' )

-- Values of this syntax are encoded according to:

-- authPasswordValue = w scheme s authInfo s authValue w
-- scheme = %x30-39 / %x41-5A / %x2D-2F / %x5F
--     ; 0-9, A-Z, "-", ".", "/", or "_"
-- authInfo = schemeSpecificValue
-- authValue = schemeSpecificValue
--         schemeSpecificValue = *( %x21-23 / %x25-7E )
--     ; printable ASCII less "$" and " "
-- s = w SEP w
-- w = *SP
-- SEP = %x24 ; "$"
-- SP = %x20 ; " " (space)
authPasswordSyntax SYNTAX-NAME ::= {
    LDAP-DESC           "authentication password syntax"
    DIRECTORY SYNTAX    AuthPasswordSyntax
    ID                  { id-at-openldap-schema 1 2 }
}

authPasswordMatch MATCHING-RULE ::= {
    SYNTAX          PlaintextPasswordSyntax
    LDAP-SYNTAX     octetString.&id
    LDAP-NAME       {"authPasswordMatch"}
    LDAP-DESC       "authentication password matching rule"
    ID              { id-at-openldap-schema 2 3 }
}

authPasswordExactMatch MATCHING-RULE ::= {
    SYNTAX          AuthPasswordSyntax
    LDAP-SYNTAX     authPasswordSyntax.&id
    LDAP-NAME       {"authPasswordExactMatch"}
    LDAP-DESC       "authentication password exact matching rule"
    ID              { id-at-openldap-schema 2 2 }
}

supportedAuthPasswordSchemes ATTRIBUTE ::= {
	WITH SYNTAX                 IA5String
    EQUALITY MATCHING RULE      caseExactIA5Match
    USAGE                       dSAOperation
    LDAP-SYNTAX                 ia5String.&id
	LDAP-NAME                   { "supportedAuthPasswordSchemes" }
	LDAP-DESC                   "supported password storage schemes"
	ID                          { id-at-openldap-schema 3 3 }
}

authPassword ATTRIBUTE ::= {
	WITH SYNTAX                 AuthPasswordSyntax
    EQUALITY MATCHING RULE      authPasswordExactMatch
    LDAP-SYNTAX                 authPasswordSyntax.&id
	LDAP-NAME                   { "authPassword" }
	LDAP-DESC                   "password authentication information"
	ID                          { id-at-openldap-schema 3 4 }
}

authPasswordObject OBJECT-CLASS ::= {
	KIND                auxiliary
    MAY CONTAIN         { authPassword }
	LDAP-NAME           { "authPasswordObject" }
	LDAP-DESC           "authentication password mix in class"
	ID                  { id-at-openldap-schema 4 7 }
}

END
