RFC5020EntryDN {
    iso(1) identified-organization(3) dod(6) internet(1) private(4)
    enterprise(1) wildboar(56490) module(1) entry-dn(30)
}
DEFINITIONS
EXPLICIT TAGS
EXTENSIBILITY IMPLIED
::=
BEGIN

EXPORTS ALL;

IMPORTS

    ATTRIBUTE, DistinguishedName, distinguishedNameMatch
        FROM InformationFramework
        {joint-iso-itu-t ds(5) module(1) informationFramework(1) 9}
        WITH SUCCESSORS

    dn
		FROM SelectedAttributeTypes
		{joint-iso-itu-t ds(5) module(1) selectedAttributeTypes(5) 9}
		WITH SUCCESSORS

    ;

-- Object Identifiers

id-at-entryDN OBJECT IDENTIFIER ::= { 1 3 6 1 1 20 }

-- Attribute Types

entryDN ATTRIBUTE ::= {
    WITH SYNTAX                 DistinguishedName
    EQUALITY MATCHING RULE 		distinguishedNameMatch
    SINGLE VALUE                TRUE
    NO USER MODIFICATION        TRUE
    USAGE                       directoryOperation
	LDAP-SYNTAX 				dn.&id
    LDAP-NAME                   {"entryDN"}
    LDAP-DESC                   "DN of the entry"
    ID                          id-at-entryDN
}

END
