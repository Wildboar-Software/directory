-- LDAP Name Service Additional Schema
-- http://www.iana.org/assignments/gssapi-service-names
NameServiceAdditionalSchema {
    iso(1) identified-organization(3) dod(6) internet(1) private(4)
    enterprise(1) wildboar(56490) module(1) name-service-additional-schema(51)
}
DEFINITIONS
EXPLICIT TAGS
EXTENSIBILITY IMPLIED
::=
BEGIN

EXPORTS ALL;

IMPORTS

    ATTRIBUTE, OBJECT-CLASS, top
        FROM InformationFramework
        {joint-iso-itu-t ds(5) module(1) informationFramework(1) 9}
        WITH SUCCESSORS

	UnboundedDirectoryString, directoryString, caseIgnoreMatch, caseIgnoreOrderingMatch
		FROM SelectedAttributeTypes
		{joint-iso-itu-t ds(5) module(1) selectedAttributeTypes(5) 9}
		WITH SUCCESSORS

    ;

authorizedService ATTRIBUTE ::= {
    WITH SYNTAX 				UnboundedDirectoryString
    EQUALITY MATCHING RULE 		caseIgnoreMatch
    ORDERING MATCHING RULE      caseIgnoreOrderingMatch
	LDAP-SYNTAX 				directoryString.&id
	LDAP-NAME 					{"authorizedService"}
    LDAP-DESC                   "IANA GSS-API authorized service name"
    ID                          { 1 3 6 1 4 1 5322 17 2 1 }
}

authorizedServiceObject OBJECT-CLASS ::= {
    SUBCLASS OF     {top}
    KIND            auxiliary
    MAY CONTAIN     {authorizedService}
	LDAP-NAME       {"authorizedServiceObject"}
    LDAP-DESC       "Auxiliary object class for adding authorizedService attribute"
	ID              { 1 3 6 1 4 1 5322 17 1 1 }
}

-- The host attribute is undefined...
-- hostObject OBJECT-CLASS ::= {
--     SUBCLASS OF     {top}
--     KIND            auxiliary
--     MAY CONTAIN     {host}
-- 	LDAP-NAME       {"hostObject"}
--     LDAP-DESC       "Auxiliary object class for adding host attribute"
-- 	ID              { 1 3 6 1 4 1 5322 17 1 2 }
-- }

END
