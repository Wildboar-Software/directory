CORBA {
    iso(1) identified-organization(3) dod(6) internet(1) private(4)
    enterprise(1) wildboar(56490) module(1) corba(22)
}
DEFINITIONS
EXPLICIT TAGS
EXTENSIBILITY IMPLIED
::=
BEGIN

EXPORTS ALL;

IMPORTS

    id-nf
        FROM Wildboar
        {iso(1) identified-organization(3) dod(6) internet(1) private(4)
        enterprise(1) wildboar(56490) module(1) wildboar(1)}
        WITH SUCCESSORS

    ATTRIBUTE, OBJECT-CLASS, top
        FROM InformationFramework
        {joint-iso-itu-t ds(5) module(1) informationFramework(1) 9}
        WITH SUCCESSORS

	directoryString, ia5String,
    caseExactMatch, caseExactOrderingMatch, caseExactSubstringsMatch,
	caseIgnoreIA5Match, caseIgnoreIA5SubstringsMatch,
    commonName, description
		FROM SelectedAttributeTypes
		{joint-iso-itu-t ds(5) module(1) selectedAttributeTypes(5) 9}
		WITH SUCCESSORS

    ;

-- Attribute Types

corbaIor ATTRIBUTE ::= {
    WITH SYNTAX 				IA5String
    EQUALITY MATCHING RULE 		caseIgnoreIA5Match
	SUBSTRINGS MATCHING RULE 	caseIgnoreIA5SubstringsMatch
    SINGLE VALUE                TRUE
	LDAP-SYNTAX 				ia5String.&id
	LDAP-NAME 					{"corbaIor"}
	LDAP-DESC					"Stringified interoperable object reference of a CORBA object"
    ID { 1 3 6 1 4 1 42 2 27 4 1 14 }
}

corbaRepositoryId ATTRIBUTE ::= {
    WITH SYNTAX 				DirectoryString
    EQUALITY MATCHING RULE 		caseExactMatch
    ORDERING MATCHING RULE      caseExactOrderingMatch
	SUBSTRINGS MATCHING RULE 	caseExactSubstringsMatch
	LDAP-SYNTAX 				directoryString.&id
	LDAP-NAME 					{"corbaRepositoryId"}
	LDAP-DESC					"Repository ids of interfaces implemented by a CORBA object"
    ID { 1 3 6 1 4 1 42 2 27 4 1 15 }
}

-- Object Classes

corbaContainer OBJECT-CLASS ::= {
    SUBCLASS OF     {top}
    KIND            structural
    MUST CONTAIN    {commonName}
    LDAP-NAME       {"corbaContainer"}
    LDAP-DESC       "Container for a CORBA object"
    ID              { 1 3 6 1 4 1 42 2 27 4 2 10 }
}

corbaObject OBJECT-CLASS ::= {
    SUBCLASS OF     {top}
    KIND            abstract
    MAY CONTAIN     {corbaRepositoryId | description}
    LDAP-NAME       {"corbaObject"}
    LDAP-DESC       "CORBA object representation"
    ID              { 1 3 6 1 4 1 42 2 27 4 2 9 }
}

corbaObjectReference OBJECT-CLASS ::= {
    SUBCLASS OF     {corbaObject}
    KIND            auxiliary
    MUST CONTAIN    {corbaIor}
    LDAP-NAME       {"corbaObjectReference"}
    LDAP-DESC       "CORBA interoperable object reference"
    ID              { 1 3 6 1 4 1 42 2 27 4 2 11 }
}

-- Name Forms

corbaContainerNameForm NAME-FORM ::= {
	NAMES				corbaContainer
	WITH ATTRIBUTES		{commonName}
	LDAP-NAME			{"corbaContainerNameForm"}
	ID					{ id-nf 51 }
}


END
