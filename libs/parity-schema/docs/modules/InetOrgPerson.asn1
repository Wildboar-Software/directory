-- InetOrgPerson (RFC2798)
InetOrgPerson {
    iso(1) identified-organization(3) dod(6) internet(1) private(4)
    enterprise(1) wildboar(56490) module(1) inetorgperson(5)
}
DEFINITIONS
EXPLICIT TAGS
EXTENSIBILITY IMPLIED
::=
BEGIN

EXPORTS ALL;

IMPORTS

    id-nf
        FROM Wildboar
        {iso(1) identified-organization(3) dod(6) internet(1) private(4)
        enterprise(1) wildboar(56490) module(1) wildboar(1)}
        WITH SUCCESSORS

    ATTRIBUTE, OBJECT-CLASS, NAME-FORM, DistinguishedName, top
        FROM InformationFramework
        {joint-iso-itu-t ds(5) module(1) informationFramework(1) 9}
        WITH SUCCESSORS

	directoryString, dn, caseIgnoreIA5Match, caseIgnoreIA5SubstringsMatch,
	ia5String, caseIgnoreListMatch, caseIgnoreListSubstringsMatch,
	caseIgnoreMatch, caseIgnoreOrderingMatch, caseIgnoreSubstringsMatch,
	commonName, UnboundedDirectoryString, jpeg, businessCategory, givenName,
    initials, organizationName, uid, uniqueIdentifier
		FROM SelectedAttributeTypes
		{joint-iso-itu-t ds(5) module(1) selectedAttributeTypes(5) 9}
		WITH SUCCESSORS

    organizationalPerson
        FROM SelectedObjectClasses
        {joint-iso-itu-t ds(5) module(1) selectedObjectClasses(6) 9}
        WITH SUCCESSORS

    audio, homeTelephoneNumber, homePostalAddress, manager,
    mobileTelephoneNumber, pagerTelephoneNumber, roomNumber, secretary
        FROM Cosine
        {iso(1) identified-organization(3) dod(6) internet(1) private(4)
        enterprise(1) wildboar(56490) module(1) cosine(3)}
        WITH SUCCESSORS

    labeledURI, mail
        FROM OpenLDAPCoreSchema
        {iso(1) identified-organization(3) dod(6) internet(1) private(4)
        enterprise(1) wildboar(56490) module(1) openldap-core(6)}

    userCertificate
        FROM AuthenticationFramework
        {joint-iso-itu-t ds(5) module(1) authenticationFramework(7) 9}
        WITH SUCCESSORS

    ;

netscapeDirectory OBJECT IDENTIFIER ::= { 2 16 840 1 113730 3 }

carLicense ATTRIBUTE ::= {
    WITH SYNTAX 				UnboundedDirectoryString
    EQUALITY MATCHING RULE 		caseIgnoreMatch
	ORDERING MATCHING RULE		caseIgnoreOrderingMatch
	SUBSTRINGS MATCHING RULE 	caseIgnoreSubstringsMatch
	LDAP-SYNTAX 				directoryString.&id
	LDAP-NAME 					{"carLicense"}
	LDAP-DESC					"RFC2798: vehicle license or registration plate"
    ID { netscapeDirectory 1 1 }
}

departmentNumber ATTRIBUTE ::= {
    WITH SYNTAX 				UnboundedDirectoryString
    EQUALITY MATCHING RULE 		caseIgnoreMatch
	ORDERING MATCHING RULE		caseIgnoreOrderingMatch
	SUBSTRINGS MATCHING RULE 	caseIgnoreSubstringsMatch
	LDAP-SYNTAX 				directoryString.&id
	LDAP-NAME 					{"departmentNumber"}
	LDAP-DESC					"RFC2798: identifies a department within an organization"
    ID { netscapeDirectory 1 2 }
}

displayName ATTRIBUTE ::= {
    WITH SYNTAX 				UnboundedDirectoryString
    EQUALITY MATCHING RULE 		caseIgnoreMatch
	ORDERING MATCHING RULE		caseIgnoreOrderingMatch
	SUBSTRINGS MATCHING RULE 	caseIgnoreSubstringsMatch
    SINGLE VALUE                TRUE
	LDAP-SYNTAX 				directoryString.&id
	LDAP-NAME 					{"displayName"}
	LDAP-DESC					"RFC2798: preferred name to be used when displaying entries"
    ID { netscapeDirectory 1 241 }
}

employeeNumber ATTRIBUTE ::= {
    WITH SYNTAX 				UnboundedDirectoryString
    EQUALITY MATCHING RULE 		caseIgnoreMatch
	ORDERING MATCHING RULE		caseIgnoreOrderingMatch
	SUBSTRINGS MATCHING RULE 	caseIgnoreSubstringsMatch
    SINGLE VALUE                TRUE
	LDAP-SYNTAX 				directoryString.&id
	LDAP-NAME 					{"employeeNumber"}
	LDAP-DESC					"RFC2798: numerically identifies an employee within an organization"
    ID { netscapeDirectory 1 3 }
}

employeeType ATTRIBUTE ::= {
    WITH SYNTAX 				UnboundedDirectoryString
    EQUALITY MATCHING RULE 		caseIgnoreMatch
	ORDERING MATCHING RULE		caseIgnoreOrderingMatch
	SUBSTRINGS MATCHING RULE 	caseIgnoreSubstringsMatch
	LDAP-SYNTAX 				directoryString.&id
	LDAP-NAME 					{"employeeType"}
	LDAP-DESC					"RFC2798: type of employment for a person"
    ID { netscapeDirectory 1 3 }
}

-- Not supported by X.500 directories.
-- jpegPhoto ATTRIBUTE ::= {
--     WITH SYNTAX 				UnboundedDirectoryString
-- 	LDAP-SYNTAX 				jpeg.&id
-- 	LDAP-NAME 					{"jpegPhoto"}
-- 	LDAP-DESC					"RFC2798: a JPEG image"
--     ID { 0 9 2342 19200300 100 1 60 }
-- }

preferredLanguage ATTRIBUTE ::= {
    WITH SYNTAX 				UnboundedDirectoryString
    EQUALITY MATCHING RULE 		caseIgnoreMatch
	ORDERING MATCHING RULE		caseIgnoreOrderingMatch
	SUBSTRINGS MATCHING RULE 	caseIgnoreSubstringsMatch
    SINGLE VALUE                TRUE
	LDAP-SYNTAX 				directoryString.&id
	LDAP-NAME 					{"preferredLanguage"}
	LDAP-DESC					"RFC2798: preferred written or spoken language for a person"
    ID { netscapeDirectory 1 39 }
}

-- userSMIMECertificate and userPKCS12 are skipped, because their syntax is
-- "binary," which is undefined (and frankly, a weakly-typed way to store files
-- like these.)

-- Object Classes

inetOrgPerson OBJECT-CLASS ::= {
	SUBCLASS OF 	{organizationalPerson}
	KIND			structural
	MAY CONTAIN		{
		audio
        | businessCategory
        | carLicense
        | departmentNumber
        | displayName
        | employeeNumber
        | employeeType
        | givenName
        | homeTelephoneNumber
        | homePostalAddress
        | initials
        -- | jpegPhoto
        | labeledURI
        | mail
        | manager
        | mobileTelephoneNumber
        | organizationName
        | pagerTelephoneNumber
        -- | photo
        | roomNumber
        | secretary
        | uid
        | userCertificate
        | uniqueIdentifier
        | preferredLanguage
        -- | userSMIMECertificate
        -- | userPKCS12
	}
	LDAP-NAME		{"inetOrgPerson"}
	LDAP-DESC		"RFC2798: Internet Organizational Person"
	ID				{ netscapeDirectory 2 2 }
}

-- Name Forms

inetOrgPersonNameForm NAME-FORM ::= {
	NAMES				inetOrgPerson
	WITH ATTRIBUTES		{commonName}
	LDAP-NAME			{"inetOrgPersonNameForm"}
	ID					{ id-nf 10 }
}

END
