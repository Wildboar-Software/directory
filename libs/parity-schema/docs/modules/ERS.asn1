ERS { iso(1) identified-organization(3) dod(6) internet(1)
    security(5) mechanisms(5) ltans(11) id-mod(0) id-mod-ers(1)
    id-mod-ers-v1(1) }
DEFINITIONS IMPLICIT TAGS ::=
BEGIN
IMPORTS

    Attribute, ATTRIBUTE
        FROM InformationFramework
        {joint-iso-itu-t ds(5) module(1) informationFramework(1) 9}
        WITH SUCCESSORS

    AlgorithmIdentifier{}, SupportedAlgorithms
        FROM AuthenticationFramework
        {joint-iso-itu-t ds(5) module(1) authenticationFramework(7) 9}

    -- ContentInfo
    --     FROM CryptographicMessageSyntax2004
    --     { iso(1) member-body(2) us(840) rsadsi(113549) pkcs(1) pkcs-9(9)
    --     smime(16) modules(0) id-mod-cms-2004-02(41) }
    ;

-- Copied from CryptographicMessageSyntax2004
ContentInfo ::= SEQUENCE {
    contentType     OBJECT IDENTIFIER,
    content         [0] EXPLICIT ANY DEFINED BY contentType }

aa-er-Internal ATTRIBUTE ::= {
    WITH SYNTAX         EvidenceRecord
    ID                  id-aa-er-internal }

id-aa-er-internal OBJECT IDENTIFIER ::=
    { iso(1) member-body(2) us(840) rsadsi(113549) pkcs(1) pkcs9(9)
    smime(16) id-aa(2) 49 }

aa-er-External ATTRIBUTE ::= {
    WITH SYNTAX         EvidenceRecord
    ID                  id-aa-er-external }

id-aa-er-external OBJECT IDENTIFIER ::=
    { iso(1) member-body(2) us(840) rsadsi(113549) pkcs(1) pkcs9(9)
    smime(16) id-aa(2) 50 }

ltans OBJECT IDENTIFIER ::=
    {iso(1) identified-organization(3) dod(6) internet(1) security(5)
    mechanisms(5) ltans(11) }

EvidenceRecord ::= SEQUENCE {
    version                   INTEGER { v1(1) } ,
    digestAlgorithms          SEQUENCE OF AlgorithmIdentifier{{SupportedAlgorithms}},
    cryptoInfos               [0] CryptoInfos OPTIONAL,
    encryptionInfo            [1] EncryptionInfo OPTIONAL,
    archiveTimeStampSequence  ArchiveTimeStampSequence
}

CryptoInfos ::= SEQUENCE SIZE (1..MAX) OF Attribute

ArchiveTimeStampSequence ::= SEQUENCE OF ArchiveTimeStampChain
ArchiveTimeStampChain    ::= SEQUENCE OF ArchiveTimeStamp

ArchiveTimeStamp ::= SEQUENCE {
    digestAlgorithm [0] AlgorithmIdentifier{{SupportedAlgorithms}} OPTIONAL,
    attributes      [1] Attributes OPTIONAL,
    reducedHashtree [2] SEQUENCE OF PartialHashtree OPTIONAL,
    timeStamp       ContentInfo
}

PartialHashtree ::= SEQUENCE OF OCTET STRING

Attributes ::= SET SIZE (1..MAX) OF Attribute

EncryptionInfo ::= SEQUENCE {
    encryptionInfoType   ENCINFO-TYPE.&id({SupportedEncryptionAlgorithms}),
    encryptionInfoValue  ENCINFO-TYPE.&Type({SupportedEncryptionAlgorithms}{@encryptionInfoType})
}

ENCINFO-TYPE ::= TYPE-IDENTIFIER

SupportedEncryptionAlgorithms ENCINFO-TYPE ::= {...}

END
