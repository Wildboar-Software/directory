-- NOTE: There are more attributes defined in core.schema, but only a few are
-- not defined in the X.500 series. This ASN.1 module just contains the
-- attribute types that were not already defined in X.520.
OpenLDAPCoreSchema {
    iso(1) identified-organization(3) dod(6) internet(1) private(4)
    enterprise(1) wildboar(56490) module(1) openldap-core(6)
}
DEFINITIONS
EXPLICIT TAGS
EXTENSIBILITY IMPLIED
::=
BEGIN

EXPORTS ALL;

IMPORTS

    ATTRIBUTE, OBJECT-CLASS, top
        FROM InformationFramework
        {joint-iso-itu-t ds(5) module(1) informationFramework(1) 9}
        WITH SUCCESSORS

	directoryString, ia5String, uid,
    caseExactMatch, caseExactOrderingMatch, caseExactSubstringsMatch,
	UnboundedDirectoryString, caseIgnoreIA5Match,
    caseIgnoreIA5SubstringsMatch
		FROM SelectedAttributeTypes
		{joint-iso-itu-t ds(5) module(1) selectedAttributeTypes(5) 9}
		WITH SUCCESSORS

    userPassword
        FROM AuthenticationFramework
        {joint-iso-itu-t ds(5) module(1) authenticationFramework(7) 9}
        WITH SUCCESSORS

    ;

labeledURI ATTRIBUTE ::= {
    WITH SYNTAX 				UnboundedDirectoryString
    EQUALITY MATCHING RULE 		caseExactMatch
	ORDERING MATCHING RULE		caseExactOrderingMatch
	SUBSTRINGS MATCHING RULE 	caseExactSubstringsMatch
	LDAP-SYNTAX 				directoryString.&id
	LDAP-NAME 					{"labeledURI"}
	LDAP-DESC					"RFC2079: Uniform Resource Identifier with optional label."
    ID { 1 3 6 1 4 1 250 1 57 }
}

-- mail ATTRIBUTE ::= {
--     WITH SYNTAX 				IA5String (SIZE (0..256))
--     EQUALITY MATCHING RULE 		caseIgnoreIA5Match
-- 	SUBSTRINGS MATCHING RULE 	caseIgnoreIA5SubstringsMatch
-- 	LDAP-SYNTAX 				ia5String.&id
-- 	LDAP-NAME 					{"mail", "rfc822Mailbox"}
-- 	LDAP-DESC					"RFC1274: RFC822 Mailbox"
--     ID { 0 9 2342 19200300 100 1 3 }
-- }

labeledURIObject OBJECT-CLASS ::= {
    SUBCLASS OF     {top}
    KIND            auxiliary
    MAY CONTAIN     {labeledURI}
    LDAP-NAME       {"labeledURIObject"}
    LDAP-DESC       "RFC2079: object that contains the URI attribute type"
    ID              { 1 3 6 1 4 1 250 3 15 }
}

simpleSecurityObject OBJECT-CLASS ::= {
    SUBCLASS OF     {top}
    KIND            auxiliary
    MUST CONTAIN    {userPassword}
    LDAP-NAME       {"simpleSecurityObject"}
    LDAP-DESC       "RFC1274: simple security object"
    ID              { 0 9 2342 19200300 100 4 19 }
}

uidObject OBJECT-CLASS ::= {
    SUBCLASS OF     {top}
    KIND            auxiliary
    MUST CONTAIN    {uid}
    LDAP-NAME       {"uidObject"}
    LDAP-DESC       "RFC2377: uid object"
    ID              { 1 3 6 1 1 3 1 }
}

END
